[DOCUMENT]
TITLE: 프로젝트 개요
UID: DOC-OVERVIEW
VERSION: 0.2
DATE: 2026-09-06
OPTIONS:
  MARKUP: RST
  AUTO_LEVELS: On

[TEXT]
STATEMENT: >>>
본 사이트는 **KAPEX-G1 협업 시연 프로젝트** (KIST Delight Robotics Lab × Unitree G1)의
시스템 요구사항 · 인터페이스 · 아키텍처 · 검증 계획을 담는다.

이 레포지토리(``KIST-DelightRobotics-G1/docs``)가 유일한 원본(SSOT)이다.
Notion의 ``SYS-REQ`` / ``ICD`` 데이터베이스는 이관 후 폐기되었다.
<<<

[[SECTION]]
TITLE: 아키텍처 조감도 (C4 Container)

[TEXT]
STATEMENT: >>>
시스템 전체의 컨테이너 배치와 주요 데이터 흐름이다. 온보드(Unitree G1 NX)와 워크스테이션(PC)의
두 실행 노드, 그 안의 컨테이너(cortex · gearsonic-inference · vla-inference · ext-sensor-io ·
safety-controller), 외부 요소(KAPEX · 클라우드 API · 디스플레이)를 한 장에 담는다.

.. image:: _assets/c4_container_architecture.svg
   :width: 100%
   :alt: KIST DRL G1 C4 Container 다이어그램

문서 칼럼에서는 축소되어 보이므로 `원본 크기로 열기 <_assets/c4_container_architecture.svg>`_
(새 탭, 브라우저에서 확대 가능).

.. note::

   이 도면은 draw.io로 **수작업** 관리하며 컨테이너가 추가·삭제될 때만 갱신한다.
   인터페이스 단위의 상세 데이터 흐름은 **아키텍처** 문서에서 ICD로부터 자동 생성된다(이원화).
   갱신 방법: draw.io에서 ``File → Export as → SVG`` 로 내보내 ``docs/_assets/c4_container_architecture.svg``
   를 교체한다. SVG 안에 draw.io 원본이 내장되어 있어 draw.io로 다시 열어 편집할 수 있다.
<<<

[[/SECTION]]

[[SECTION]]
TITLE: 문서 구성

[TEXT]
STATEMENT: >>>
.. list-table::
   :widths: 30 70
   :header-rows: 1

   * - 문서
     - 내용
   * - 시스템 요구사항 (SYS-REQ)
     - 추적 트리의 최상위. 기능(FR) · 비기능(NFR) · 안전(SR) 요구사항.
   * - 인터페이스 정의서 (ICD)
     - 컨테이너 간 인터페이스. ``Implements`` 관계로 SYS-REQ를, ``File`` 관계로 구현 파일을 가리킨다.
       경로(섹션)마다 ICD 노드에서 자동 생성한 데이터 흐름도가 머리에 붙는다.
   * - 검증 계획 (TEST CASE)
     - 요구사항의 수용 확인 항목. 시연으로 확인하는 항목은 ``Demonstration``.

추적 체인은 **요구사항 → 인터페이스 → 구현 파일 → 검증** 이다.
<<<

[[/SECTION]]

[[SECTION]]
TITLE: 화면 안내

[TEXT]
STATEMENT: >>>
좌측 사이드바에서 문서를 선택한 뒤, 각 문서 상단의 탭으로 네 가지 화면을 전환할 수 있다.

.. list-table:: 문서별 화면
   :widths: 22 78
   :header-rows: 1

   * - 화면
     - 용도
   * - **DOC**
     - 사람이 읽는 문서. 리뷰 회의에서 띄우는 화면.
   * - **TABLE**
     - 요구사항을 표로. 필드가 컬럼이 된다.
   * - **TRACE**
     - 좌우 2단. 각 노드의 부모·자식을 한 단계 확인한다.
   * - **DEEP-TRACE**
     - 최상위 요구사항부터 구현·검증까지 전 체인을 한 화면에 표시한다.

프로젝트 전체 화면은 좌측 최상단 아이콘에서 접근한다.

.. list-table:: 프로젝트 화면
   :widths: 22 78
   :header-rows: 1

   * - 화면
     - 용도
   * - **Project tree**
     - 문서 목록.
   * - **Traceability matrix**
     - 요구사항 × 관계 행렬. 연결이 빠진 항목을 한눈에 찾는다.
   * - **Source coverage**
     - 요구사항별 구현 파일 연결 현황. 미구현 요구사항을 검출한다.
   * - **Project statistics**
     - 요구사항 수, 상태 분포, 커버리지 요약.
   * - **Search**
     - 전체 노드 검색.
<<<

[[/SECTION]]

[[SECTION]]
TITLE: 운영 규칙

[TEXT]
STATEMENT: >>>
- 필드명은 영어, 본문은 한글로 쓴다. 선택지 값은 ``docs/kist_g1.sgra`` 에 정의된 토큰만 허용된다.
- 변경은 브랜치 → PR → 리뷰 → ``main`` 머지로만 반영한다. 머지되면 CI가 사이트를 갱신한다.
- ICD를 수정하면 ``python tools/gen_arch.py`` 로 ICD 섹션 흐름도를 다시 생성한다.
- 시연 마일스톤마다 git 태그를 남기고, 릴리스 간 변경은 Diff/Changelog로 확인한다.
<<<

[[/SECTION]]
