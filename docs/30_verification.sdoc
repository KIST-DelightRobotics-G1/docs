[DOCUMENT]
TITLE: KIST DRL G1 검증 계획 (TEST CASE)
UID: DOC-TEST
VERSION: 0.2
DATE: 2026-09-06
CLASSIFICATION: Internal
OPTIONS:
  MARKUP: RST
  AUTO_LEVELS: On
  NODE_IN_TOC: True

[GRAMMAR]
IMPORT_FROM_FILE: kist_g1.sgra

[TEXT]
STATEMENT: >>>
본 문서는 시스템 요구사항의 **수용 확인 항목** 을 정의한다.

이 프로젝트의 요구사항은 별도의 시험이 아니라 **시연(Demonstration)** 으로 수용을 확인한다.
KIST MBO 시연 시나리오 3단계의 각 단계가 검증 항목이 되며 ``METHOD: Demonstration`` 으로 표기한다.
시연으로 확인할 수 없는 성능 수치(제어 주기 유지율, 통신 왕복 지연)만 ``METHOD: Test`` (계측)로 둔다.

각 검증 항목은 ``Verifies`` 관계로 상위 시스템 요구사항에 연결된다.
**Traceability matrix** 에서 어떤 시연 단계에서도 다뤄지지 않는 요구사항이 드러나고,
**DEEP-TRACE** 에서 요구사항 → 인터페이스 → 구현 파일 → 검증의 전체 체인이 한 화면에 나타난다.

.. note::

   시연 공통 조건 — KAPEX는 조리대 앞 고정, G1은 조리대 ↔ 냉장고 사이를 이동한다.
   복구(recovery)는 sub-task당 최대 1회이며, 2회 이상 지연되면 해당 단계를 건너뛴다.
<<<

[[SECTION]]
TITLE: 시연 1단계 — 단일 객체 인식 및 전달

[TEXT]
STATEMENT: >>>
KAPEX: "G1, 냉장고에서 오이 하나 가져다주세요."
G1: ① 냉장고 이동 → ② 문 개방 → ③ 오이 파지 → ④ 조리대 tray 안착.
cortex 시나리오 ``refrigerator_pickup.json5`` 의 sub-task 4개에 대응한다.
<<<

[TEST_CASE]
UID: TC-101
TITLE: 음성 명령으로 시나리오 트리거
METHOD: Demonstration
STATEMENT: >>>
1. KAPEX가 "G1, 냉장고에서 오이 하나 가져다주세요" 라고 발화한다.
2. G1이 발화를 인식하여 ``refrigerator_pickup`` 시나리오를 시작한다.
3. 첫 sub-task 진입 시 G1이 "냉장고 앞으로 갑니다" 라고 안내한다.
<<<
EXPECTED: >>>
발화 후 수 초 내에 시나리오가 시작되고 안내 음성이 스피커로 출력된다.
안내 음성이 재생되는 동안 G1이 자기 음성을 명령으로 오인식하지 않는다.
<<<
RELATIONS:
- TYPE: Parent
  VALUE: SYS-REQ-27
  ROLE: Verifies
- TYPE: Parent
  VALUE: SYS-REQ-29
  ROLE: Verifies
- TYPE: Parent
  VALUE: SYS-REQ-44
  ROLE: Verifies

[TEST_CASE]
UID: TC-102
TITLE: 냉장고 접근 (approach_fridge)
METHOD: Demonstration
STATEMENT: >>>
1. 발화 "냉장고에서 오이 하나 가져다줘" 에서 LLM 이 첫 subtask ``move_to(fridge)`` 를 내고,
   오케스트레이터가 END 를 기다리지 않고 바로 발사한다 (ICD-77 · ICD-78 · ICD-70).
2. G1이 조리대에서 냉장고 앞까지 자율 보행한다.
3. nav 이 ``SubtaskState`` 를 ``DONE`` 으로 돌려주고, 오케스트레이터가 ``at`` 을 ``fridge`` 로 갱신한다.
<<<
EXPECTED: >>>
G1이 장애물과 충돌 없이 냉장고 정면에 정지하고, ``DONE`` 수신 후 다음 subtask 로 진행한다.
step timeout(nav 60 s) 내에 도달하지 못하거나 ``FAILED`` 가 오면 "냉장고로 이동하지 못했습니다"
안내 후 계획을 중단하고, ``at`` 은 ``unknown`` 으로 되돌아간다.
<<<
RELATIONS:
- TYPE: Parent
  VALUE: SYS-REQ-45
  ROLE: Verifies
- TYPE: Parent
  VALUE: SYS-REQ-42
  ROLE: Verifies
- TYPE: Parent
  VALUE: SYS-REQ-32
  ROLE: Verifies
- TYPE: Parent
  VALUE: SYS-REQ-44
  ROLE: Verifies

[TEST_CASE]
UID: TC-103
TITLE: 냉장고 문 개방 (open_door)
METHOD: Demonstration
STATEMENT: >>>
1. 조작 직전에 오케스트레이터가 ``CheckTarget(fridge_door)`` 로 대상이 지금 보이는지 확인한다 (ICD-79).
2. 확인되면 ``open(fridge_door)`` 을 ``instruction`` "Open the refrigerator door." 와 함께 VLA 로 발사한다 (ICD-75).
3. VLA 정책이 카메라·관절 상태로부터 전신 동작을 생성하고, 균형 보정을 거쳐 관절 명령으로 실행된다.
<<<
EXPECTED: >>>
G1이 균형을 잃지 않고 문을 열며, 동작 중 관절 명령이 끊기거나 급격히 튀지 않는다.
VLA 가 ``DONE`` 을 돌려주면 다음 subtask 로 진행한다.

사전 확인이 "안 보임" 이면 "냉장고 문이 보이지 않습니다" 안내 후 계획을 중단한다. 검출기가
없거나 프레임이 없어 **판정 자체가 불가능한 경우는 진행한다**\ (fail-open) — 판정기 고장으로
로봇이 서 버리는 쪽이 더 나쁘다.
<<<
RELATIONS:
- TYPE: Parent
  VALUE: SYS-REQ-31
  ROLE: Verifies
- TYPE: Parent
  VALUE: SYS-REQ-39
  ROLE: Verifies
- TYPE: Parent
  VALUE: SYS-REQ-43
  ROLE: Verifies
- TYPE: Parent
  VALUE: SYS-REQ-34
  ROLE: Verifies
- TYPE: Parent
  VALUE: SYS-REQ-44
  ROLE: Verifies

[TEST_CASE]
UID: TC-104
TITLE: 오이 파지 (grasp_cucumber)
METHOD: Demonstration
STATEMENT: >>>
1. ``CheckTarget(cucumber)`` 로 오이가 보이는지 확인한 뒤 (냉장고는 확인하지 않는다, cortex #46)
   ``take_out(cucumber, fridge)`` 를 VLA 학습 문장 "Reach out with the right hand and pick up the
   cucumber inside the fridge." 와 함께 발사한다 (``pick(cucumber)`` 과 같은 문장, cortex #45).
2. G1이 오이를 인식하고 파지한다.
3. VLA 가 ``DONE`` 을 돌려주면 오케스트레이터가 ``holding`` 을 ``cucumber`` 로 갱신한다.
<<<
EXPECTED: >>>
오이가 떨어뜨려지지 않고 그리퍼에 유지된 상태로 ``DONE`` 이 오고, ``holding`` 이 갱신된다.
``FAILED`` 면 ``holding`` 은 ``none`` 으로 남아, 다음 계획이 집기를 다시 넣어 회복한다.
<<<
COMMENT: >>>
성공 여부는 VLA 가 돌려주는 ``status`` 로만 판단한다. ``progress`` 는 추정값이라 판정에 쓰지 않는다.
파지 판정을 joint_state(기하) 와 묶어 강화하는 것은 별건으로 남아 있다.
<<<
RELATIONS:
- TYPE: Parent
  VALUE: SYS-REQ-31
  ROLE: Verifies
- TYPE: Parent
  VALUE: SYS-REQ-44
  ROLE: Verifies

[TEST_CASE]
UID: TC-105
TITLE: 조리대 이동 및 tray 안착 (place_on_tray)
METHOD: Demonstration
STATEMENT: >>>
1. ``close(fridge_door)`` → ``move_to(user)`` → ``handover(cucumber, user)`` 가 차례로 발사된다.
   ``move_to`` 는 nav, 나머지는 VLA 로 나간다 (``config/actions.yaml`` 의 ``exec``).
2. G1이 오이를 든 채 사용자에게 보행한 뒤 건넨다.
3. 마지막 ``DONE`` 과 ``END`` 를 함께 받으면 계획이 완료되고, ``holding`` 이 ``none`` 으로 돌아간다.
<<<
EXPECTED: >>>
이동 중 파지 상태가 유지되고, 오이가 tray 지정 위치에 놓인다. 완료 안내 음성("모두 마쳤습니다.", cortex #41)이 출력되며 시나리오가 정상 종료된다.
<<<
RELATIONS:
- TYPE: Parent
  VALUE: SYS-REQ-45
  ROLE: Verifies
- TYPE: Parent
  VALUE: SYS-REQ-31
  ROLE: Verifies
- TYPE: Parent
  VALUE: SYS-REQ-29
  ROLE: Verifies
- TYPE: Parent
  VALUE: SYS-REQ-44
  ROLE: Verifies

[TEST_CASE]
UID: TC-106
TITLE: 시연 중 실시간 모니터링
METHOD: Demonstration
STATEMENT: >>>
1. 시연 시작 전 외부 디스플레이(브라우저)를 GUI 브리지에 연결한다.
2. TC-101 ~ TC-105 진행 중 디스플레이를 관찰한다.
<<<
EXPECTED: >>>
디스플레이에 현재 시나리오명 · sub-task 이름과 순번 · 상태(active/success/failed)가 카메라 영상 위에
오버레이되어 실시간으로 갱신된다. 영상과 실제 동작 사이의 지연이 체감상 0.2 s 이내이다.
<<<
RELATIONS:
- TYPE: Parent
  VALUE: SYS-REQ-41
  ROLE: Verifies
- TYPE: Parent
  VALUE: SYS-REQ-49
  ROLE: Verifies
- TYPE: Parent
  VALUE: SYS-REQ-42
  ROLE: Verifies

[TEST_CASE]
UID: TC-107
TITLE: 실패 복구 및 단계 건너뛰기
METHOD: Demonstration
STATEMENT: >>>
1. 임의의 sub-task(예: ``grasp_cucumber``)가 timeout 내에 성공 판정을 받지 못하게 한다 (오이를 손이 닿지 않는 곳에 둔다).
2. G1의 실패 안내 음성과 복구 시도를 관찰한다.
3. 복구가 1회 더 실패하면 해당 단계를 건너뛰고 시연을 계속한다.
<<<
EXPECTED: >>>
실패 시 "오이를 집지 못했습니다" 안내가 출력되고, 복구는 최대 1회만 시도된다.
2회 지연 시 단계를 건너뛰며, 시스템이 무한 대기하거나 정지하지 않는다.
<<<
RELATIONS:
- TYPE: Parent
  VALUE: SYS-REQ-44
  ROLE: Verifies
- TYPE: Parent
  VALUE: SYS-REQ-29
  ROLE: Verifies

[TEST_CASE]
UID: TC-108
TITLE: 긴급 정지 및 PC 링크 단절 시 안전 거동
METHOD: Demonstration
STATEMENT: >>>
1. G1이 동작 중(예: TC-103 진행 중)일 때 E-STOP을 발효한다.
2. 관절 명령 발행이 차단되고 로봇이 안전 자세로 정지하는지 관찰한다.
3. (별도 회차) PC ↔ 로봇 LAN을 분리하여 명령 스트림을 끊는다.
<<<
EXPECTED: >>>
E-STOP 발효 즉시 진행 중인 동작·발화가 중단되고 로봇이 넘어지지 않는다.
PC 링크 단절 시 로봇이 주저앉지 않고 기립 자세를 유지한 뒤, 온보드 워치독이 내장 균형 제어기로
제어권을 이관한다. PC 복귀만으로는 제어권이 자동 반환되지 않는다.
<<<
COMMENT: 기립 시퀀스의 첫 실기 확인은 반드시 호이스트에 매단 상태로 수행한다.
RELATIONS:
- TYPE: Parent
  VALUE: SYS-REQ-35
  ROLE: Verifies
- TYPE: Parent
  VALUE: SYS-REQ-34
  ROLE: Verifies

[[/SECTION]]

[[SECTION]]
TITLE: 시연 2단계 — 다중 객체 · Occlusion · 공간 언어

[TEXT]
STATEMENT: >>>
KAPEX: "오이와 양상추를 바구니에 담아주세요." → 가려진 양상추 해소 → "제 오른쪽에 내려놓아 주세요."
<<<

[TEST_CASE]
UID: TC-201
TITLE: 다중 객체 순차 파지 및 담기
METHOD: Demonstration
STATEMENT: >>>
1. KAPEX가 "오이와 양상추를 바구니에 담아주세요" 라고 발화한다.
2. G1이 두 객체를 순차적으로 파지하여 바구니에 담는다.
<<<
EXPECTED: >>>
하나의 발화로 두 객체에 대한 sub-task 시퀀스가 실행되고, 두 객체 모두 바구니에 담긴다.
<<<
RELATIONS:
- TYPE: Parent
  VALUE: SYS-REQ-44
  ROLE: Verifies
- TYPE: Parent
  VALUE: SYS-REQ-31
  ROLE: Verifies
- TYPE: Parent
  VALUE: SYS-REQ-27
  ROLE: Verifies

[TEST_CASE]
UID: TC-202
TITLE: 가려진 객체(occlusion) 해소
METHOD: Demonstration
STATEMENT: >>>
1. 양상추 앞에 다른 물체를 두어 카메라에서 부분적으로 가려지게 배치한다.
2. G1이 가리는 물체를 옮기거나 시점을 바꿔 양상추를 인식·파지하는지 관찰한다.
<<<
EXPECTED: >>>
G1이 가림을 인지하고 해소 동작 후 양상추를 파지한다. 가림 상태에서 오파지(다른 물체를 집음)가 발생하지 않는다.
<<<
RELATIONS:
- TYPE: Parent
  VALUE: SYS-REQ-31
  ROLE: Verifies
- TYPE: Parent
  VALUE: SYS-REQ-44
  ROLE: Verifies

[TEST_CASE]
UID: TC-203
TITLE: 공간 언어 해석 ("제 오른쪽에")
METHOD: Demonstration
STATEMENT: >>>
1. KAPEX가 "제 오른쪽에 내려놓아 주세요" 라고 발화한다.
2. G1이 KAPEX 기준 오른쪽 위치로 이동하여 바구니를 내려놓는다.
<<<
EXPECTED: >>>
"오른쪽" 이 G1이 아니라 **KAPEX 기준** 으로 해석되어, 바구니가 KAPEX의 오른편 조리대 위에 놓인다.
<<<
RELATIONS:
- TYPE: Parent
  VALUE: SYS-REQ-27
  ROLE: Verifies
- TYPE: Parent
  VALUE: SYS-REQ-44
  ROLE: Verifies
- TYPE: Parent
  VALUE: SYS-REQ-45
  ROLE: Verifies
- TYPE: Parent
  VALUE: SYS-REQ-31
  ROLE: Verifies

[[/SECTION]]

[[SECTION]]
TITLE: 시연 3단계 — 의미 추론 및 병렬 협업

[TEXT]
STATEMENT: >>>
발사믹 부재 시 "오리엔탈 드레싱으로 대체할까요?" → 양 로봇 타이밍 동기화하여 드레싱 주입 + 버무리기.
<<<

[TEST_CASE]
UID: TC-301
TITLE: 부재 인지 및 대체 제안 대화
METHOD: Demonstration
STATEMENT: >>>
1. 발사믹 드레싱을 냉장고에서 제거해 둔다.
2. KAPEX가 발사믹 드레싱을 요청한다.
3. G1이 부재를 인지하고 "오리엔탈 드레싱으로 대체할까요?" 라고 묻는다.
4. KAPEX가 "네" 라고 답하면 G1이 오리엔탈 드레싱을 가져온다.
<<<
EXPECTED: >>>
G1이 요청 물품의 부재를 장면에서 판단하고 대체안을 음성으로 제안한다.
KAPEX의 응답을 인식하여 대체 물품으로 시나리오를 계속한다.
<<<
RELATIONS:
- TYPE: Parent
  VALUE: SYS-REQ-27
  ROLE: Verifies
- TYPE: Parent
  VALUE: SYS-REQ-29
  ROLE: Verifies
- TYPE: Parent
  VALUE: SYS-REQ-44
  ROLE: Verifies

[TEST_CASE]
UID: TC-302
TITLE: 양 로봇 타이밍 동기화 협업
METHOD: Demonstration
STATEMENT: >>>
1. KAPEX가 샐러드를 버무릴 준비가 되면 G1에게 드레싱 주입을 요청한다.
2. G1이 KAPEX의 버무리기 동작에 맞춰 드레싱을 주입한다.
<<<
EXPECTED: >>>
두 로봇의 동작이 시간적으로 맞물려(주입 → 버무리기) 드레싱이 흘리지 않고 샐러드에 들어간다.
<<<
RELATIONS:
- TYPE: Parent
  VALUE: SYS-REQ-44
  ROLE: Verifies
- TYPE: Parent
  VALUE: SYS-REQ-31
  ROLE: Verifies

[[/SECTION]]

[[SECTION]]
TITLE: 계측 항목 (시연으로 확인 불가)

[TEXT]
STATEMENT: >>>
수치 성능 요구사항은 시연 관찰로 판정할 수 없어 로그 계측으로 확인한다.
<<<

[TEST_CASE]
UID: TC-401
TITLE: 저수준 제어 주기 유지율 계측
METHOD: Test
STATEMENT: >>>
1. gearsonic을 로봇에 연결하여 10분 이상 운용한다 (시연 1단계 전체 포함).
2. Cmd Writers의 지터 로그에서 500 Hz 주기 유지율을 산출한다.
<<<
EXPECTED: >>>
목표 주기 유지율 ≥ 99 %.
<<<
RELATIONS:
- TYPE: Parent
  VALUE: SYS-REQ-38
  ROLE: Verifies
- TYPE: Parent
  VALUE: SYS-REQ-34
  ROLE: Verifies

[TEST_CASE]
UID: TC-402
TITLE: PC ↔ 로봇 통신 왕복 지연 계측
METHOD: Test
STATEMENT: >>>
1. PC에서 ``rt/lowcmd`` 발행 시각과 ``rt/lowstate`` 로 반영되는 시각을 기록한다.
2. 유선 LAN 환경에서 1분 이상 측정하여 왕복 지연 분포를 산출한다.
<<<
EXPECTED: >>>
왕복 지연 ≤ 5 ms, 20 Hz 이상 주기로 끊김 없이 동작.
<<<
RELATIONS:
- TYPE: Parent
  VALUE: SYS-REQ-32
  ROLE: Verifies

[[/SECTION]]
