[DOCUMENT]
TITLE: KIST DRL G1 아키텍처
UID: DOC-ARCH
VERSION: 0.1
DATE: 2026-09-05
CLASSIFICATION: Internal
OPTIONS:
  MARKUP: RST
  AUTO_LEVELS: On

[TEXT]
STATEMENT: >>>
.. warning::

   본 문서는 ``tools/gen_arch.py`` 가 ``docs/20_icd.sdoc`` 에서 **자동 생성** 한다.
   직접 편집하지 말 것. 편집해도 다음 생성 시 덮어써진다.

본 문서는 시스템의 컨테이너 구성과 컨테이너 간 데이터 흐름을 정의한다.
아래 다이어그램은 손으로 그린 것이 아니라 인터페이스 정의서(ICD)에서 생성된다.
각 ``[ICD]`` 노드의 ``송신 컨테이너`` / ``수신 컨테이너`` 가 화살표의 양 끝이고,
``통신 방식`` 이 선 모양이 된다.

.. code-block:: text

   python tools/gen_arch.py

ICD를 수정한 뒤 위 명령을 다시 실행하면 다이어그램이 갱신된다.
CI에서 ``python tools/gen_arch.py --check`` 를 돌리면
"ICD는 바뀌었는데 다이어그램은 안 바뀐" 상태를 빌드 실패로 잡을 수 있다.

현재 인터페이스 34건.
<<<

[[SECTION]]
TITLE: 읽는 법

[TEXT]
STATEMENT: >>>
다이어그램은 ICD 문서의 섹션(데이터 경로) 단위로 나누어 그린다.
전체를 한 장에 그리면 문서 폭에서 글씨를 읽을 수 없기 때문이다.

**선 모양**

- 실선 — DDS 토픽
- 점선 — DDS 외 통신 (HTTPS · gRPC · WebSocket)

**구현 상태** 는 도면에 표시하지 않는다. 각 인터페이스가 구현 파일에 연결되었는지는
**Source coverage** 화면과 각 ICD 노드의 ``File`` 관계에서 확인한다.

화살표 라벨은 ICD 번호이며, 토픽 상세는 각 그림 아래 표에 있다.
<<<

[[/SECTION]]

[[SECTION]]
TITLE: 음성 입력 경로 (STT)

[TEXT]
STATEMENT: >>>
.. raw:: html

   <div style="overflow-x:auto; max-width:100%;">
   <pre class="mermaid">
      flowchart TB
        subgraph onboard["Unitree G1 (NX) — Onboard"]
          n_ext_sensor_io["ext-sensor-io"]
          n_speaker_node["speaker_node"]
        end
        subgraph workstation["PC (RTX 4090) — Workstation"]
          n_stt_node["stt_node"]
          n_orchestrator_node["orchestrator_node"]
        end
        subgraph external["External"]
          n_Google_Cloud_STT["Google Cloud STT"]
        end

        n_ext_sensor_io -->|"ICD-3"| n_stt_node
        n_stt_node -.->|"ICD-33"| n_Google_Cloud_STT
        n_stt_node -->|"ICD-64"| n_orchestrator_node
        n_speaker_node -->|"ICD-42"| n_stt_node
   </pre>
   </div>

.. list-table::
   :widths: 10 22 22 46
   :header-rows: 1

   * - ID
     - 송신
     - 수신
     - 토픽 / 엔드포인트
   * - ICD-3
     - ext-sensor-io
     - stt_node
     - ``rt/kist/mic/<name>/audio``
   * - ICD-33
     - stt_node
     - Google Cloud STT
     - ``google.cloud.speech.v1``
   * - ICD-64
     - stt_node
     - orchestrator_node
     - ``/cortex/stt/transcript``
   * - ICD-42
     - speaker_node
     - stt_node
     - ``/cortex/speaker/state``

<<<

[[/SECTION]]

[[SECTION]]
TITLE: 음성 출력 경로 (TTS)

[TEXT]
STATEMENT: >>>
.. raw:: html

   <div style="overflow-x:auto; max-width:100%;">
   <pre class="mermaid">
      flowchart TB
        subgraph onboard["Unitree G1 (NX) — Onboard"]
          n_G1["G1"]
          n_speaker_node["speaker_node"]
        end
        subgraph workstation["PC (RTX 4090) — Workstation"]
          n_orchestrator_node["orchestrator_node"]
          n_tts_node["tts_node"]
        end
        subgraph external["External"]
          n_Naver_CLOVA_TTS["Naver CLOVA TTS"]
        end

        n_orchestrator_node -->|"ICD-68"| n_tts_node
        n_tts_node -.->|"ICD-34"| n_Naver_CLOVA_TTS
        n_tts_node -->|"ICD-8"| n_speaker_node
        n_speaker_node -->|"ICD-86"| n_G1
        n_orchestrator_node -->|"ICD-69"| n_tts_node
        n_orchestrator_node -->|"ICD-83"| n_tts_node
   </pre>
   </div>

.. list-table::
   :widths: 10 22 22 46
   :header-rows: 1

   * - ID
     - 송신
     - 수신
     - 토픽 / 엔드포인트
   * - ICD-68
     - orchestrator_node
     - tts_node
     - ``/cortex/tts/say``
   * - ICD-34
     - tts_node
     - Naver CLOVA TTS
     - ``REST API``
   * - ICD-8
     - tts_node
     - speaker_node
     - ``/cortex/tts/audio``
   * - ICD-86
     - speaker_node
     - G1
     - ``rt/api/voice/request · rt/api/voice/response``
   * - ICD-69
     - orchestrator_node
     - tts_node
     - ``/cortex/tts/stop``
   * - ICD-83
     - orchestrator_node
     - tts_node
     - ``/cortex/tts/prefetch · /cortex/tts/warmup``

<<<

[[/SECTION]]

[[SECTION]]
TITLE: 시나리오 실행 및 판정

[TEXT]
STATEMENT: >>>
.. raw:: html

   <div style="overflow-x:auto; max-width:100%;">
   <pre class="mermaid">
      flowchart TB
        subgraph workstation["PC (RTX 4090) — Workstation"]
          n_orchestrator_node["orchestrator_node"]
          n_gearsonic["gearsonic"]
          n_nav_planner["nav-planner"]
          n_Cortex["Cortex"]
        end
        n_Gemini_API["Gemini API (구역 미지정)"]
        n_detector_node["detector_node (구역 미지정)"]
        n_llm_node["llm_node (구역 미지정)"]
        n_vla_inference["vla-inference (구역 미지정)"]

        n_orchestrator_node -->|"ICD-70"| n_nav_planner
        n_nav_planner -->|"ICD-74"| n_orchestrator_node
        n_orchestrator_node -->|"ICD-75"| n_vla_inference
        n_vla_inference -->|"ICD-76"| n_orchestrator_node
        n_orchestrator_node -->|"ICD-77"| n_llm_node
        n_llm_node -->|"ICD-78"| n_orchestrator_node
        n_orchestrator_node -->|"ICD-79"| n_detector_node
        n_llm_node -.->|"ICD-81"| n_Gemini_API
        n_nav_planner -->|"ICD-82"| n_orchestrator_node
        n_detector_node -->|"ICD-84"| n_Cortex
        n_nav_planner -->|"ICD-72"| n_gearsonic
   </pre>
   </div>

.. list-table::
   :widths: 10 22 22 46
   :header-rows: 1

   * - ID
     - 송신
     - 수신
     - 토픽 / 엔드포인트
   * - ICD-70
     - orchestrator_node
     - nav-planner
     - ``rt/cortex/nav/cmd``
   * - ICD-74
     - nav-planner
     - orchestrator_node
     - ``rt/cortex/nav/state``
   * - ICD-75
     - orchestrator_node
     - vla-inference
     - ``rt/cortex/vla/cmd``
   * - ICD-76
     - vla-inference
     - orchestrator_node
     - ``rt/cortex/vla/state``
   * - ICD-77
     - orchestrator_node
     - llm_node
     - ``/cortex/llm/request``
   * - ICD-78
     - llm_node
     - orchestrator_node
     - ``/cortex/llm/step``
   * - ICD-79
     - orchestrator_node
     - detector_node
     - ``/cortex/detector/check``
   * - ICD-81
     - llm_node
     - Gemini API
     - ``google-genai streaming``
   * - ICD-82
     - nav-planner
     - orchestrator_node
     - ``rt/kist/nav/destinations``
   * - ICD-84
     - detector_node
     - Cortex
     - ``/cortex/detections``
   * - ICD-72
     - nav-planner
     - gearsonic
     - ``rt/kist/nav/cmd_vel``

<<<

[[/SECTION]]

[[SECTION]]
TITLE: 모니터링 및 디스플레이

[TEXT]
STATEMENT: >>>
.. raw:: html

   <div style="overflow-x:auto; max-width:100%;">
   <pre class="mermaid">
      flowchart TB
        subgraph onboard["Unitree G1 (NX) — Onboard"]
          n_ext_sensor_io["ext-sensor-io"]
        end
        subgraph workstation["PC (RTX 4090) — Workstation"]
          n_orchestrator_node["orchestrator_node"]
          n_gui_bridge_node["gui_bridge_node"]
        end
        subgraph external["External"]
          n_Display_Renderer["Display Renderer"]
        end
        n_detector_node["detector_node (구역 미지정)"]

        n_ext_sensor_io -->|"ICD-62"| n_detector_node
        n_orchestrator_node -->|"ICD-67"| n_gui_bridge_node
        n_orchestrator_node -->|"ICD-80"| n_gui_bridge_node
        n_gui_bridge_node -.->|"ICD-55"| n_Display_Renderer
   </pre>
   </div>

.. list-table::
   :widths: 10 22 22 46
   :header-rows: 1

   * - ID
     - 송신
     - 수신
     - 토픽 / 엔드포인트
   * - ICD-62
     - ext-sensor-io
     - detector_node
     - ``rt/kist/camera/<name>/color/h264``
   * - ICD-67
     - orchestrator_node
     - gui_bridge_node
     - ``/cortex/task_status``
   * - ICD-80
     - orchestrator_node
     - gui_bridge_node
     - ``/cortex/trace``
   * - ICD-55
     - gui_bridge_node
     - Display Renderer
     - ``ws://<cortex-host>:8081``

<<<

[[/SECTION]]

[[SECTION]]
TITLE: 센서 입력 (측위 · 인지)

[TEXT]
STATEMENT: >>>
.. raw:: html

   <div style="overflow-x:auto; max-width:100%;">
   <pre class="mermaid">
      flowchart TB
        subgraph onboard["Unitree G1 (NX) — Onboard"]
          n_G1["G1"]
          n_ext_sensor_io["ext-sensor-io"]
        end
        subgraph workstation["PC (RTX 4090) — Workstation"]
          n_nav_planner["nav-planner"]
        end
        n_FAST_LIO_engine["FAST-LIO engine (구역 미지정)"]

        n_ext_sensor_io -->|"ICD-36"| n_nav_planner
        n_G1 -->|"ICD-58"| n_FAST_LIO_engine
        n_FAST_LIO_engine -->|"ICD-85"| n_nav_planner
        n_ext_sensor_io -->|"ICD-63"| n_nav_planner
   </pre>
   </div>

.. list-table::
   :widths: 10 22 22 46
   :header-rows: 1

   * - ID
     - 송신
     - 수신
     - 토픽 / 엔드포인트
   * - ICD-36
     - ext-sensor-io
     - nav-planner
     - ``rt/kist/uwb/pose``
   * - ICD-58
     - G1
     - FAST-LIO engine
     - ``/livox/lidar``
   * - ICD-85
     - FAST-LIO engine
     - nav-planner
     - ``rt/Odometry_loc · rt/cloud_registered_1``
   * - ICD-63
     - ext-sensor-io
     - nav-planner
     - ``rt/kist/camera/<name>/depth/rvl``

<<<

[[/SECTION]]

[[SECTION]]
TITLE: 저수준 제어 및 안전

[TEXT]
STATEMENT: >>>
.. raw:: html

   <div style="overflow-x:auto; max-width:100%;">
   <pre class="mermaid">
      flowchart TB
        subgraph onboard["Unitree G1 (NX) — Onboard"]
          n_G1["G1"]
        end
        subgraph workstation["PC (RTX 4090) — Workstation"]
          n_gearsonic["gearsonic"]
        end

        n_G1 -->|"ICD-4"| n_gearsonic
        n_G1 -->|"ICD-41"| n_gearsonic
        n_gearsonic -->|"ICD-50"| n_G1
        n_gearsonic -->|"ICD-6"| n_G1
        n_G1 -->|"ICD-73"| n_gearsonic
   </pre>
   </div>

.. list-table::
   :widths: 10 22 22 46
   :header-rows: 1

   * - ID
     - 송신
     - 수신
     - 토픽 / 엔드포인트
   * - ICD-4
     - G1
     - gearsonic
     - ``rt/lowstate``
   * - ICD-41
     - G1
     - gearsonic
     - ``rt/secondary_imu``
   * - ICD-50
     - gearsonic
     - G1
     - ``rt/lowcmd``
   * - ICD-6
     - gearsonic
     - G1
     - ``rt/dex3/{left,right}/cmd``
   * - ICD-73
     - G1
     - gearsonic
     - ``rt/dex3/{left,right}/state``

<<<

[[/SECTION]]
