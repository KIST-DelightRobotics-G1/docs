[DOCUMENT]
TITLE: KIST DRL G1 인터페이스 정의서 (ICD)
UID: DOC-ICD
VERSION: 0.4
DATE: 2026-10-03
CLASSIFICATION: Internal
OPTIONS:
  MARKUP: RST
  AUTO_LEVELS: On
  NODE_IN_TOC: True

[GRAMMAR]
IMPORT_FROM_FILE: kist_g1.sgra

[TEXT]
STATEMENT: >>>
본 문서는 KAPEX-G1 협업 시연 시스템의 컨테이너 간 **인터페이스(ICD)** 를 정의한다.

각 인터페이스는 ``Implements`` 관계로 상위 시스템 요구사항(SYS-REQ)에 연결되며,
``File`` 관계로 송·수신 양측의 구현 파일을 가리킨다. **TRACE / DEEP-TRACE** 화면에서
요구사항 → 인터페이스 → 구현 파일의 연결을 확인할 수 있다.
구현 파일은 빌드 시 ``tools/fetch_sources.py`` 가 ``_src/<repo>/`` 로 체크아웃한다.

각 섹션(데이터 경로)은 **소개 → 흐름도 → 인터페이스** 순서다. 흐름도는 손으로 그리지 않고
``tools/gen_arch.py`` 가 그 섹션의 ICD 노드에서 생성한다. 화살표의 양 끝은 송·수신
컨테이너, 라벨은 ICD 번호, 실선은 DDS 토픽, 점선은 DDS 외 통신(HTTPS · gRPC · WebSocket)이다.
구현 상태는 그림에 표시하지 않는다 — 각 노드의 ``File`` 관계와 **Source coverage** 화면에서 확인한다.

.. note::

   본 문서는 Notion ``ICD`` 데이터베이스(22건)를 이관한 것이며(이후 ICD-72부터는 코드 동기화로 추가), UID 번호는 Notion 시절
   Interface ID를 그대로 잇는다. Notion의 선택지 값 중 괄호가 있는 것은 StrictDoc 문법상
   ``Getter (Pull)`` → ``Getter``, ``Call (Push)`` → ``Call`` 로 정규화하였다.
<<<

[[SECTION]]
TITLE: 음성 입력 경로 (STT)

[TEXT]
STATEMENT: >>>
마이크 → STT → orchestrator 로 이어지는 음성 인식 경로이다.
``SYS-REQ-42`` (센서 수집) 와 ``SYS-REQ-27`` (음성 인식) 을 함께 구현한다.
<<<

[TEXT]
STATEMENT: >>>
.. gen_arch: 아래 흐름도는 tools/gen_arch.py 가 이 섹션의 ICD 노드에서 생성한다. 직접 편집하지 말 것.

.. raw:: html

   <div style="overflow-x:auto; max-width:100%;">
   <pre class="mermaid">
      flowchart TB
        subgraph onboard["Unitree G1 (NX) — Onboard"]
          n_ext_sensor_io["ext-sensor-io"]
        end
        subgraph workstation["PC (RTX 4090) — Workstation"]
          n_stt_node["stt_node"]
          n_speaker_node["speaker_node"]
          n_orchestrator_node["orchestrator_node"]
        end
        subgraph external["External"]
          n_Google_Cloud_STT["Google Cloud STT"]
        end

        n_ext_sensor_io -->|"ICD-3"| n_stt_node
        n_stt_node -.->|"ICD-33"| n_Google_Cloud_STT
        n_stt_node -->|"ICD-64"| n_orchestrator_node
        n_speaker_node -->|"ICD-42"| n_stt_node
   </pre>
   </div>
<<<

[ICD]
UID: ICD-3
TITLE: Mic Audio (ext-sensor → stt)
COMM_TYPE: DDS Topic
SOURCE: ext-sensor-io
TARGET: stt_node
TOPIC: rt/kist/mic/<name>/audio
MSG_TYPE: kist_msgs::msg::dds_::AudioChunk_
QOS: BestEffort
FREQUENCY: continuous (100 ms chunk)
STATEMENT: >>>
``seq`` + ``stamp_ns`` + ``sample_rate`` + ``channels`` + ``format`` (``S16_LE``) + ``frame_id``
+ ``data`` (interleaved PCM). 100 ms 청크 단위, 장치 그대로의 속도 · 채널로 발행한다.
데모 PC 마이크는 ``uno`` (ESI NEVA UNO, 44.1 kHz × 2 ch, 하드웨어 에코 억제 없음),
로봇 마이크는 ``array`` (reSpeaker XVF3800, 16 kHz × 6 ch).

타입 이름이 ROS 2 형식이라 cortex 는 ROS 메시지 ``kist_msgs/AudioChunk`` 로 바로 구독한다.
토픽은 ``stt_node.audio_topic`` (기본 ``/kist/mic/uno/audio``) 이고, **0 번 채널** 만 꺼내 16 kHz 로
맞춘다 (XVF3800 이면 0 번이 빔포밍 출력).
<<<
PRECONDITION: mic(ALSA) 활성
COMMENT: >>>
2026-09-28: ext-sensor-io ``48c6ca9`` (#3) 가 타입 이름을 ``kist_msgs::AudioChunk`` 에서 ROS 2 형식으로
바꾸고, cortex ``728a492`` (#23) 가 도메인 0 에서 직접 읽는다. 예전에 계획한 변환 노드(mic_bridge)는
만들지 않는다. 6 채널을 평균 내면 처리된 소리에 원본 잡음이 섞이므로 0 번 채널을 쓴다.

2026-10-06: ext-sensor-io ``8ec20e9`` 가 UNO 를 44.1 kHz 로 바꿨다 (장치 클럭이 44100 만 지원해
48000 요청이 거부됨). cortex ``08a37c2`` (#34) 가 데모 PC 기본 마이크를 UNO 로 바꿨다.
<<<
RELATIONS:
- TYPE: Parent
  VALUE: SYS-REQ-42
  ROLE: Implements
- TYPE: Parent
  VALUE: SYS-REQ-27
  ROLE: Implements
- TYPE: File
  VALUE: _src/ext-sensor-io/src/mic/transmitter/audio_publisher.cpp
- TYPE: File
  VALUE: _src/ext-sensor-io/src/system/mic_transmitter.cpp
- TYPE: File
  VALUE: _src/cortex/src/cortex_perception/cortex_perception/stt_node.py
- TYPE: File
  VALUE: _src/cortex/src/cortex_perception/cortex_perception/ext_sensor.py
- TYPE: File
  VALUE: _src/cortex/src/kist_msgs/msg/AudioChunk.msg
- TYPE: File
  VALUE: _src/ext-sensor-io/idl/kist_audio_frames.idl

[ICD]
UID: ICD-33
TITLE: STT API (Google Cloud)
COMM_TYPE: gRPC
SOURCE: stt_node
TARGET: Google Cloud STT
MSG_TYPE: google.cloud.speech.v1
QOS: N/A
FREQUENCY: Streaming
STATEMENT: >>>
``audio: bytes`` → ``transcript: str``, ``confidence: float``
<<<
PRECONDITION: API key 설정 + 네트워크
RELATIONS:
- TYPE: Parent
  VALUE: SYS-REQ-27
  ROLE: Implements
- TYPE: File
  VALUE: _src/cortex/src/cortex_perception/cortex_perception/stt_node.py

[ICD]
UID: ICD-64
TITLE: STT Transcript (stt → orchestrator)
COMM_TYPE: DDS Topic
SOURCE: stt_node
TARGET: orchestrator_node
TOPIC: /cortex/stt/transcript
MSG_TYPE: std_msgs/String
QOS: Reliable
FREQUENCY: On-demand (is_final)
STATEMENT: >>>
``data: str`` — 최종 인식 문장(is_final). orchestrator가 시나리오 trigger 키워드와 매칭한다.
<<<
PRECONDITION: stt_node 활성 (Google Cloud STT 스트리밍)
COMMENT: OM IF-20 대체.
RELATIONS:
- TYPE: Parent
  VALUE: SYS-REQ-27
  ROLE: Implements
- TYPE: File
  VALUE: _src/cortex/src/cortex_perception/cortex_perception/stt_node.py
- TYPE: File
  VALUE: _src/cortex/src/cortex_cognition/cortex_cognition/orchestrator_node.py

[ICD]
UID: ICD-42
TITLE: Speaker State (speaker → stt)
COMM_TYPE: DDS Topic
SOURCE: speaker_node
TARGET: stt_node
TOPIC: /cortex/speaker/state
MSG_TYPE: g1_onboard_msgs/SpeakerState
QOS: Reliable
FREQUENCY: 상태 변화 시 (push/pop transition)
STATEMENT: >>>
``playing(bool)`` + ``current_chunk_id(uint32)`` + ``queue_depth(uint8)``.

stt_node는 ``playing=true`` 인 동안 마이크를 뮤트하여 자체 음성 오인식을 방지한다(에코 캔슬).

``playing`` 은 "보냈다" 가 아니라 "로봇이 아직 말하고 있다" 이다. ``PlayStream`` 은 로봇 쪽 버퍼에 넣고
바로 돌아오므로, speaker_node 가 보낸 음성 길이로 재생이 끝날 시각을 계산해 그때까지 ``true`` 를 유지한다
(cortex #25). 끼어들기가 오면 즉시 ``false`` 가 된다.
<<<
PRECONDITION: speaker_node 활성 (AudioClient)
COMMENT: >>>
speaker_node 가 cortex 에 들어왔다 (#24). 토픽 이름은 comm_bridge 시절의 ``/bridge/audio/speaker_state``
에서 ``/cortex/speaker/state`` 로 바뀌었다.
<<<
RELATIONS:
- TYPE: Parent
  VALUE: SYS-REQ-27
  ROLE: Implements
- TYPE: File
  VALUE: _src/cortex/src/cortex_action/cortex_action/speaker_node.py
- TYPE: File
  VALUE: _src/cortex/src/cortex_perception/cortex_perception/stt_node.py
- TYPE: File
  VALUE: _src/interface-msgs/msg/SpeakerState.msg

[[/SECTION]]

[[SECTION]]
TITLE: 음성 출력 경로 (TTS)

[TEXT]
STATEMENT: >>>
orchestrator → TTS → 스피커로 이어지는 음성 응답 경로이다. ``SYS-REQ-29`` 를 구현한다.
<<<

[TEXT]
STATEMENT: >>>
.. gen_arch: 아래 흐름도는 tools/gen_arch.py 가 이 섹션의 ICD 노드에서 생성한다. 직접 편집하지 말 것.

.. raw:: html

   <div style="overflow-x:auto; max-width:100%;">
   <pre class="mermaid">
      flowchart TB
        subgraph onboard["Unitree G1 (NX) — Onboard"]
          n_G1["G1"]
        end
        subgraph workstation["PC (RTX 4090) — Workstation"]
          n_speaker_node["speaker_node"]
          n_orchestrator_node["orchestrator_node"]
          n_tts_node["tts_node"]
        end
        subgraph external["External"]
          n_Naver_CLOVA_TTS["Naver CLOVA TTS"]
        end

        n_orchestrator_node -->|"ICD-68"| n_tts_node
        n_tts_node -.->|"ICD-34"| n_Naver_CLOVA_TTS
        n_tts_node -->|"ICD-8"| n_speaker_node
        n_speaker_node -->|"ICD-86"| n_G1
        n_orchestrator_node -->|"ICD-69"| n_tts_node
        n_orchestrator_node -->|"ICD-83"| n_tts_node
   </pre>
   </div>
<<<

[ICD]
UID: ICD-68
TITLE: Action Cmd — Speak (orchestrator → tts)
COMM_TYPE: DDS Topic
SOURCE: orchestrator_node
TARGET: tts_node
TOPIC: /cortex/tts/say
MSG_TYPE: cortex_msgs/ActionCmd
QOS: Reliable
FREQUENCY: On-demand
STATEMENT: >>>
``text: str`` — 말할 내용(payload).

open-loop 설계: orchestrator는 발사 후 확인하지 않는다 (``command_id`` / ``status`` 없음).

단계를 시작할 때 계획 줄의 ``say`` 를, 단계가 DONE 이면 완료 문장(``actions.yaml`` ``done_say``,
예 "냉장고 문을 열었습니다.") 을 보낸다. 마지막 단계는 "모두 마쳤습니다." 로 끝난다. 시작 문장이 없는
단계(시연 보정 삽입)는 완료 문장도 없다. ``say_on_done: false`` 면 완료 문장을 끈다 (cortex #41).
<<<
PRECONDITION: orchestrator speak connector dispatch
COMMENT: OM IF-26/31 대체.
RELATIONS:
- TYPE: Parent
  VALUE: SYS-REQ-29
  ROLE: Implements
- TYPE: File
  VALUE: _src/cortex/src/cortex_cognition/cortex_cognition/orchestrator_node.py
- TYPE: File
  VALUE: _src/cortex/src/cortex_action/cortex_action/tts_node.py
- TYPE: File
  VALUE: _src/cortex/src/cortex_msgs/msg/ActionCmd.msg

[ICD]
UID: ICD-34
TITLE: TTS API (Naver CLOVA)
COMM_TYPE: HTTPS
SOURCE: tts_node
TARGET: Naver CLOVA TTS
MSG_TYPE: REST API
QOS: N/A
FREQUENCY: On-demand
STATEMENT: >>>
``text: str``, ``speaker: str`` → ``audio: bytes`` (mp3/wav)
<<<
PRECONDITION: API key 설정 + 네트워크
RELATIONS:
- TYPE: Parent
  VALUE: SYS-REQ-29
  ROLE: Implements
- TYPE: File
  VALUE: _src/cortex/src/cortex_action/cortex_action/tts_node.py

[ICD]
UID: ICD-8
TITLE: TTS Audio Out (tts → speaker)
COMM_TYPE: DDS Topic
SOURCE: tts_node
TARGET: speaker_node
TOPIC: /cortex/tts/audio
MSG_TYPE: g1_onboard_msgs/AudioPCM
QOS: Reliable
FREQUENCY: On-demand
STATEMENT: >>>
16 kHz / mono / 16 bit PCM. CLOVA 24 kHz 출력을 16 kHz로 resample 후 32000 B (≈ 1 s) 조각으로 발행한다.
speaker_node가 ``AudioClient.PlayStream`` 으로 재생한다 (ICD-86). ``header.stamp`` 는 끼어들기 때
그 전에 만든 조각을 가려내는 데 쓴다 (ICD-69).
<<<
PRECONDITION: TTS 합성 완료 + speaker_node(AudioClient) 활성
COMMENT: >>>
speaker_node 가 cortex 에 들어왔다 (#24). 토픽 이름은 ``/bridge/cmd/audio_out`` 에서 ``/cortex/tts/audio``
로 바뀌었다. AudioClient 재생은 DDS RPC 라 로봇이 DDS 로 보이는 호스트면 된다.
<<<
RELATIONS:
- TYPE: Parent
  VALUE: SYS-REQ-29
  ROLE: Implements
- TYPE: File
  VALUE: _src/cortex/src/cortex_action/cortex_action/tts_node.py
- TYPE: File
  VALUE: _src/cortex/src/cortex_action/cortex_action/speaker_node.py
- TYPE: File
  VALUE: _src/interface-msgs/msg/AudioPCM.msg

[ICD]
UID: ICD-86
TITLE: Speaker Playback RPC (speaker_node → G1 audio service)
COMM_TYPE: Call
SOURCE: speaker_node
TARGET: G1
TOPIC: rt/api/voice/request · rt/api/voice/response
MSG_TYPE: unitree_api::msg::dds_::Request_ · Response_
QOS: Reliable
FREQUENCY: 음성 조각마다 (최대 32000 B ≈ 1 s)
STATEMENT: >>>
Unitree SDK ``AudioClient`` 로 G1 오디오 서비스(``voice``)를 부르는 DDS RPC 다.
``PlayStream`` (api 1003) 은 ``{app_name, stream_id}`` JSON 과 16 kHz · mono · 16 bit PCM 을
``binary`` 에 실어 보내고, ``PlayStop`` (api 1004) 은 재생을 끊는다.
한 문장이 한 ``stream_id`` 이고, 끼어들기 뒤의 문장은 새 ``stream_id`` 로 시작한다.

두 호출 모두 응답을 기다린다 (``client_timeout_s`` 2 s). 기다리는 동안 speaker_node 는
"재생 중" 을 알리므로 stt_node 의 마이크가 음소거된다.
<<<
PRECONDITION: G1 오디오 서비스 기동 + 도메인 0 에서 서비스 호스트가 보일 것
COMMENT: >>>
cortex ``SYS-REQ-29-speaker-node`` (#24). onboard 의 speaker_node 를 옮겼다 (onboard 는 더 쓰지 않음).
rclpy 와 unitree_sdk2py 가 한 프로세스에서 같은 libddsc 를 쓰도록, 도커 이미지가 SDK 의 cyclonedds
파이썬 바인딩을 ROS 의 CycloneDDS 로 빌드한다.

오디오 서비스는 G1 내부 PC 에서 돈다. Unitree 서비스를 포함한 로봇 쪽 모듈이 모두 멀티캐스트로
탐색하므로 cortex 도 멀티캐스트로 찾는다 (cortex #25 — 유니캐스트 전용이던 이전 설정은 로봇 쪽과
서로를 찾지 못했다). ``DDS_ROBOT_IP`` (기본 ``192.168.123.161``) 는 보조 peer 다.

speaker_node 는 로봇 버퍼에 1.5 s (``lead_s``) 넘게 쌓이지 않도록 조각을 보내는 속도를 맞춘다.
<<<
RELATIONS:
- TYPE: Parent
  VALUE: SYS-REQ-29
  ROLE: Implements
- TYPE: File
  VALUE: _src/cortex/src/cortex_action/cortex_action/speaker_node.py
- TYPE: File
  VALUE: _src/cortex/config/cyclonedds.xml

[ICD]
UID: ICD-69
TITLE: Barge-in Stop (orchestrator → tts)
COMM_TYPE: DDS Topic
SOURCE: orchestrator_node
TARGET: tts_node
TOPIC: /cortex/tts/stop
MSG_TYPE: std_msgs/Bool
QOS: Reliable
FREQUENCY: On-demand
STATEMENT: >>>
``data: bool`` (true = 말 끊기).

"그만" · 새 발화로 인한 선점 때 orchestrator 가 발사한다. fire-and-forget.

- tts_node: 진행 중인 합성을 취소한다.
- speaker_node: 받은 시각 **이전에 발행된** 음성 조각을 큐와 전송 중인 것까지 버리고 ``PlayStop`` 을
  부른다. 그 뒤에 오는 문장("멈춥니다.")은 새 stream 으로 재생된다.
<<<
PRECONDITION: orchestrator preempt/fail 경로
COMMENT: >>>
2026-09-28: E-STOP 입력은 쓰지 않기로 해 stt · tts 에서 뺐다 (cortex ``c241f96``, #22).
speaker_node 도 이 토픽을 받는다 (#24) — 예전 onboard speaker_node 는 큐에 든 음성을 끝까지 재생했다.
<<<
RELATIONS:
- TYPE: Parent
  VALUE: SYS-REQ-29
  ROLE: Implements
- TYPE: File
  VALUE: _src/cortex/src/cortex_cognition/cortex_cognition/orchestrator_node.py
- TYPE: File
  VALUE: _src/cortex/src/cortex_action/cortex_action/tts_node.py
- TYPE: File
  VALUE: _src/cortex/src/cortex_action/cortex_action/speaker_node.py

[ICD]
UID: ICD-83
TITLE: TTS Prefetch (orchestrator → tts)
COMM_TYPE: DDS Topic
SOURCE: orchestrator_node
TARGET: tts_node
TOPIC: /cortex/tts/prefetch · /cortex/tts/warmup
MSG_TYPE: cortex_msgs/ActionCmd
QOS: Reliable
FREQUENCY: 이벤트 (다음 단계 확정 시 · 기동 후 1회)
STATEMENT: >>>
말할 문장을 **미리** 보내 합성 결과만 캐시에 채워 둔다 (재생하지 않는다). ``prefetch`` 는
다음 subtask 의 ``say`` 와 그 단계의 완료 문장(cortex #41)을, ``warmup`` 은 기동 직후 고정 문구와
예시 문장을 대상으로 한다.
<<<
PRECONDITION: tts_node 기동
COMMENT: >>>
캐시에 있으면 4~24 ms 에 재생이 시작되고, 없으면 CLOVA 합성에 0.3~1.4초가 걸린다.
계획이 스트리밍으로 오므로 다음 문장을 미리 알 수 있어 성립하는 최적화다 (SYS-REQ-29).
<<<
RELATIONS:
- TYPE: Parent
  VALUE: SYS-REQ-29
  ROLE: Implements
- TYPE: File
  VALUE: _src/cortex/src/cortex_cognition/cortex_cognition/orchestrator_node.py
- TYPE: File
  VALUE: _src/cortex/src/cortex_action/cortex_action/tts_node.py

[[/SECTION]]

[[SECTION]]
TITLE: 시나리오 실행 및 판정

[TEXT]
STATEMENT: >>>
발화에서 subtask 를 만들고(LLM), 조작 직전에 대상을 확인하고(detector),
실행 모듈(nav / VLA)에 나눠 보내는 경로이다. 성공 여부는 모듈이 돌려주는 상태로만 판정한다.
``SYS-REQ-44`` (시나리오 실행) 를 중심으로 ``SYS-REQ-31`` / ``SYS-REQ-45`` 의 명령 진입점을 포함한다.
<<<

[TEXT]
STATEMENT: >>>
.. gen_arch: 아래 흐름도는 tools/gen_arch.py 가 이 섹션의 ICD 노드에서 생성한다. 직접 편집하지 말 것.

.. raw:: html

   <div style="overflow-x:auto; max-width:100%;">
   <pre class="mermaid">
      flowchart TB
        subgraph workstation["PC (RTX 4090) — Workstation"]
          n_orchestrator_node["orchestrator_node"]
          n_llm_node["llm_node"]
          n_detector_node["detector_node"]
          n_vla_inference["vla-inference"]
          n_gearsonic["gearsonic"]
          n_nav_planner["nav-planner"]
          n_Cortex["Cortex"]
        end
        subgraph external["External"]
          n_Gemini_API["Gemini API"]
        end

        n_orchestrator_node -->|"ICD-70"| n_nav_planner
        n_nav_planner -->|"ICD-74"| n_orchestrator_node
        n_orchestrator_node -->|"ICD-75"| n_vla_inference
        n_vla_inference -->|"ICD-76"| n_orchestrator_node
        n_orchestrator_node -->|"ICD-77"| n_llm_node
        n_llm_node -->|"ICD-78"| n_orchestrator_node
        n_orchestrator_node -->|"ICD-79"| n_detector_node
        n_llm_node -.->|"ICD-81"| n_Gemini_API
        n_nav_planner -->|"ICD-82"| n_orchestrator_node
        n_detector_node -->|"ICD-84"| n_Cortex
        n_nav_planner -->|"ICD-72"| n_gearsonic
   </pre>
   </div>
<<<

[TEXT]
UID: RULE-SUBTASK
STATEMENT: >>>
**Subtask 실행 규약** — ICD-70 · 74 (nav) 와 ICD-75 · 76 (VLA) 가 함께 지키는 주고받기 규칙이다.

오케스트레이터는 LLM 계획의 한 줄(subtask)을 nav 또는 VLA 에 하나씩 보내고, **모듈이 보고하는
status 만으로** 완료·실패를 판정한다. 완료 기준(nav 도착 반경, VLA 진행도 임계 등)은 모듈 내부의
일이라 여기서 정하지 않는다. 하드웨어 E-STOP 은 안전 계층이 직접 처리하므로 이 규약 밖이다.

**1. 모듈 상태 기계** (nav · VLA 가 지킨다)

.. list-table::
   :widths: 18 28 18 36
   :header-rows: 1

   * - 현재
     - 사건
     - 다음
     - 규칙
   * - IDLE
     - Cmd 수신 (``cancel=false``)
     - RUNNING
     - 수신 후 100 ms 안에 RUNNING 을 처음 발행한다
   * - IDLE
     - Cmd 수신, 미지원 action · 불량 args · 빈 instruction (VLA)
     - FAILED
     - ``detail`` = ``unsupported: <무엇이>``
   * - IDLE
     - cancel 수신
     - IDLE
     - 무시
   * - RUNNING
     - 모듈 자체 완료 판정
     - DONE
     - 기준은 모듈 내부 (nav 도착 반경 · VLA 진행도 임계)
   * - RUNNING
     - 모듈 자체 실패 판정
     - FAILED
     - ``detail`` 필수 (``no path`` · ``grasp lost`` · ``timeout 30s`` …)
   * - RUNNING
     - 같은 id 의 cancel, 즉시 정지 가능
     - IDLE
     - 멈춘 뒤 ``detail`` ``cancelled`` 로 IDLE
   * - RUNNING
     - 같은 id 의 cancel, 즉시 정지가 위험
     - RUNNING
     - ``detail`` ``cancel_deferred: <이유>`` 로 안전 지점까지만 진행한 뒤
       IDLE ``cancelled_at_safe_point``. 원래 목표는 마치지 않는다
   * - RUNNING
     - 다른 id 의 cancel
     - RUNNING
     - 무시
   * - RUNNING
     - Cmd 수신 (같은 id 재전송 포함)
     - RUNNING
     - 무시. 오케스트레이터는 IDLE 인 모듈에만 Cmd 를 보낸다 (3 절) — **Cmd 로 하는 선점은 없다**
   * - DONE · FAILED
     - 3회(0.3 s) 발행 완료
     - IDLE
     -
   * - DONE · FAILED
     - 3회 중 Cmd 수신
     - 모듈 재량
     - 받아서 시작하거나 무시한다 (vla-inference 는 받는다). 오케스트레이터는 IDLE 뒤에만 보내므로 생기지 않는다

**2. 발행 규칙** (모듈)

- 10 Hz 상시 발행한다. IDLE 도 낸다. 시작 직후 첫 메시지는 IDLE 이다.
- ``plan_id`` · ``index`` · ``action`` 은 받은 Cmd 값을 그대로 되돌린다. IDLE 이면 ``""`` / ``0``.
- ``stamp_ns`` 는 발행 시각(epoch ns)이다. 오케스트레이터가 신선도 판정에 쓴다.
- 한 subtask 의 결과(DONE 또는 FAILED)는 하나다. 3회 반복은 같은 결과의 재발행이며, 그 뒤 같은
  index 로 RUNNING 을 다시 내지 않는다.
- ``progress`` 는 0~1, 없으면 0. 디버그·표시용이며 판정에 쓰지 않는다.
- **IDLE 은 "정리 완료, 새 Cmd 받을 수 있음" 이다.** IDLE 을 내기 전에 동작 정지와 내부 큐 ·
  스레드 정리를 끝낸다.

**3. 판정 규칙** (오케스트레이터)

- **Cmd 는 마지막 보고가 IDLE 인 모듈에만 보낸다.** 모든 Cmd(새 계획의 첫 단계, 다른 모듈로
  넘어가는 단계 포함)에 적용한다. IDLE 이 아니면 보내지 않고 IDLE 을 기다린다. 그 모듈이
  버려진 이전 단계로 아직 RUNNING 이면 보고된 id 로 cancel 을 보낸다. ``safe_stop_timeout_s``
  안에 IDLE 이 없으면 아무것도 보내지 않고 계획을 중단하며 사용자에게 알린다.
  IDLE 을 확인한 뒤 Cmd 를 보내기 전에 대상 확인(``RULE-PRECHECK``)을 거친다.
- **단계가 끝나면 DONE 이 아니라 IDLE 을 기다린다.** 같은 id 의 DONE 을 받으면 그 단계를
  완료로 기록하고, 그 모듈이 IDLE 을 보낼 때 다음 Cmd 를 보낸다. ``idle_wait_s`` 안에 IDLE 이
  없으면 계획을 중단한다. nav 와 VLA 는 둘 다 gearsonic 으로 몸을 움직이므로 "도착"(DONE) 이
  아니라 "손 뗌"(IDLE) 을 확인하고 넘긴다.
- **모든 멈춤은 cancel → IDLE 이다.** 사용자 "그만", 새 발화로 계획을 바꿀 때, 단계 타임아웃 모두
  cancel 을 즉시 보내고 IDLE 을 기다린다 (4 절). 예외는 계획 도중 LLM 오류 하나로, 이때는 현재
  단계를 끝까지 두되 단계 타임아웃을 넘기면 취소한다.
- ``plan_id`` · ``index`` 가 현재 단계와 다른 상태는 무시한다 (이전 계획의 늦은 보고 등). 같은 id 의
  DONE · FAILED 는 한 번만 판정한다.
- Cmd 를 보낸 뒤 ``accept_timeout_s`` 안에 같은 id 의 RUNNING 이 없으면 1회 재전송하고, 그래도
  없으면 단계 실패(``not accepted``) 로 계획을 중단한다.
- 마지막 상태 수신 후 ``stale_s`` 가 지나면 모듈 상실로 보고 계획을 중단한다.
- RUNNING 이 ``step_timeout_s`` 를 넘기면 cancel 을 보내고 단계 실패로 처리한다.
- FAILED 는 계획 중단과 안내 문구로 끝난다. 재시도는 하지 않는다.
- 남은 단계가 없고 LLM 의 ``end`` 를 받았으면 계획 완료다. ``end`` 가 없으면 ``step_wait_s``
  동안 다음 줄을 기다린다. ``end`` 는 경계 표시일 뿐이며 성공의 근거는 언제나 모듈의 DONE 이다.
- 한 시점에 실행 중인 subtask 는 하나다. 두 모듈에 동시에 Cmd 를 보내지 않는다.

**4. 취소** (새 발화로 계획을 바꿀 때 포함)

1. 실행 중에 새 발화가 오면, 오케스트레이터는 새 계획의 줄을 받아 두기만 하고(실행하지 않음) 첫 줄이
   오는 순간 현재 단계를 멈추기로 한다. 사용자 "그만" 은 계획 없이 바로 멈춘다.
2. 오케스트레이터가 현재 ``plan_id`` · ``index`` 로 ``cancel=true`` 를 보낸다.
3. 모듈은 ``cancel_ack_s`` 안에 IDLE (``cancelled``) 또는 RUNNING (``cancel_deferred: …``) 으로 답한다.
4. 유예면 오케스트레이터는 ``safe_stop_timeout_s`` 동안 새 Cmd 를 보류하고 IDLE 을 기다린다.
5. IDLE 이 오면 받아 둔 새 계획의 첫 Cmd 를 보낸다. 시간 안에 IDLE 이 없으면 **새 계획을 시작하지 않고**
   사용자에게 알린다.

Cmd 로 하는 선점이 없으므로 **cancel 이 멈추는 유일한 경로다.** ``cancel_ack_s`` 안에 IDLE 도
``cancel_deferred`` 도 없으면 cancel 을 1회 재전송한다. 즉시 멈출지 안전 지점까지 갈지는 모듈이 정한다.

**5. 시간 파라미터**

.. list-table::
   :widths: 26 22 16 36
   :header-rows: 1

   * - 이름
     - 값
     - 소유
     - 비고
   * - 상태 발행 주기
     - 10 Hz
     - 모듈
     - heartbeat 겸용
   * - RUNNING 첫 발행
     - 100 ms 이내
     - 모듈
     -
   * - DONE · FAILED 반복
     - 3회 (0.3 s)
     - 모듈
     - RELIABLE QoS 전제의 유실 대비
   * - 완료 기준
     - 모듈 내부
     - 모듈
     - 예: VLA 진행도 0.7
   * - ``accept_timeout_s``
     - 0.5 s (+1회 재전송)
     - 오케스트레이터
     -
   * - ``stale_s``
     - 1.0 s
     - 오케스트레이터
     - 10 Hz 에서 10회 연속 누락
   * - ``idle_wait_s``
     - 1.0 s
     - 오케스트레이터
     - DONE → IDLE
   * - ``step_timeout_s``
     - nav 60 s · VLA 30 s
     - 오케스트레이터
     - 실기 측정 후 조정
   * - ``step_wait_s``
     - 5 s
     - 오케스트레이터
     - 다음 계획 줄 대기
   * - ``cancel_ack_s``
     - 0.5 s
     - 오케스트레이터
     - IDLE 또는 ``cancel_deferred`` 응답 기한. 넘기면 cancel 1회 재전송
   * - ``safe_stop_timeout_s``
     - nav 3 s · VLA 10 s
     - 오케스트레이터
     - 안전 지점 도달 여유

**6. detail 문자열**

.. list-table::
   :widths: 34 66
   :header-rows: 1

   * - 값
     - 언제
   * - ``""``
     - 보통의 RUNNING · DONE · IDLE
   * - ``cancelled``
     - cancel 을 받고 즉시 멈춘 뒤의 IDLE
   * - ``cancel_deferred: <이유>``
     - cancel 을 받았으나 안전 지점까지 진행 중인 RUNNING
   * - ``cancelled_at_safe_point``
     - 유예 후 안전 지점에서 멈춘 IDLE
   * - ``unsupported: <이유>``
     - 미지원 action · 불량 args · 빈 instruction 으로 FAILED
   * - ``timeout <초>s``
     - 모듈 내부 시간 초과로 FAILED
   * - 그 외 자유 문자열
     - FAILED 사유 (``no path`` · ``grasp lost`` …). 로그 · GUI 표시용

**7. VLA instruction 어휘**

vla-inference 의 진행도 헤드는 ``probes.json`` (학습 문장 → 헤드 파일) 에서 받은 ``instruction`` 과
**글자까지 같은 키** 의 헤드만 고른다. 다르면 진행도 판정이 없어 DONE 이 오지 않고 단계 타임아웃으로
끝난다. 그래서 VLA 단계의 ``instruction`` 은 **VLA 학습 문장과 글자까지 같아야 한다.**

- **문장의 원본은 cortex** ``src/cortex_cognition/config/vla_prompts.yaml`` 이다. 키는 ``동작(인자)``
  (예 ``open(fridge_door)``), 값은 ``probes.json`` 의 키 문장 그대로다. **VLA 담당이 채운다.**
- 오케스트레이터는 이 표를 먼저 찾고, 없거나 비어 있으면 ``config/actions.yaml`` · ``plan_rewrites.yaml``
  의 템플릿 문장을 보내며 경고를 남긴다 (기동 로그 ``NOT FILLED`` 목록, VLA 전송마다 경고).
- 학습 문장을 바꾸면 이 파일도 같이 고친다.

.. list-table::
   :widths: 34 66
   :header-rows: 1

   * - 키 (시연 동작)
     - 표가 비어 있을 때 보내는 템플릿 문장
   * - ``open(fridge_door)`` — **기입됨**
     - Open the refrigerator door.
   * - ``approach(fridge)`` — 시연 보정 삽입, **기입됨**
     - Approach the refrigerator.
   * - ``pick(cucumber)`` — **기입됨**
     - Pick up the cucumber.
   * - ``take_out(cucumber,fridge)`` — **기입됨** (``pick(cucumber)`` 과 같은 문장)
     - Take the cucumber out of the refrigerator.
   * - ``step_back(fridge)`` — 시연 보정 삽입
     - Step back from the refrigerator.
   * - ``close(fridge_door)``
     - Close the refrigerator door.
   * - ``place(cucumber,table)``
     - Place the cucumber on the table.
   * - ``handover(cucumber,user)``
     - Hand the cucumber to the person.

2026-10-15 현재 open · approach · pick 은 VLA 학습 문장이 들어가 있다 (cortex #31). 시연 발화에 LLM 은
매번 ``take_out(cucumber, fridge)`` 를 내므로 같은 동작인 ``pick`` 의 문장을 그대로 쓴다 (cortex #45).
``step_back`` · ``close`` · ``place`` · ``handover`` 는 비어 있다 — VLA 팀 확인 필요.
<<<

[TEXT]
UID: RULE-PRECHECK
STATEMENT: >>>
**사전 확인 규약** — orchestrator_node 와 detector_node 가 ICD-79 로 지키는 판정 규칙이다 (cortex #29).
조작 Cmd 를 보내기 전에 대상이 카메라에 보이는지 확인해, 대상이 없는데 VLA 가 움직이는 일을 막는다.

**1. 언제 무엇을 묻나**

대상 모듈이 IDLE 이 된 뒤(``RULE-SUBTASK`` 3 절), Cmd 를 보내기 직전에 ``config/actions.yaml`` 의
``precheck`` 표대로 묻는다. 값이 목록이면 **모두 보여야** 한다 (AND). 표에 없는 동작
(``move_to`` · ``place`` · ``approach`` · ``step_back`` 등)은 묻지 않는다.

.. list-table::
   :widths: 45 55
   :header-rows: 1

   * - 시연 동작
     - 확인 대상
   * - ``open(fridge_door)`` · ``close(fridge_door)``
     - ``fridge_door``
   * - ``take_out(cucumber,fridge)``
     - ``cucumber`` (냉장고는 확인하지 않는다, cortex #46)
   * - ``pick(cucumber)``
     - ``cucumber`` (냉장고는 확인하지 않는다)
   * - ``handover(cucumber,user)``
     - ``user``

**2. detector 판정**

새로 추론하지 않고 최근 ``window_s`` (0.6 s) 창에서 답한다. 서로 다른 원본 프레임이 ``min_frames``
(3) 장 이상 있어야 하고, 신뢰도가 기준 이상인 프레임이 **과반**\ 이며, ``require_latest_hit`` 이면 가장
최근 프레임에서도 검출되어야 "보임" 이다. 프레임 나이는 영상 원본 시각으로 재므로 송 · 수신 PC 의
시계가 맞아야 하고, 오래되었거나 미래 시각인 프레임은 버린다.

**3. 결과별 오케스트레이터 동작**

.. list-table::
   :widths: 34 14 24 28
   :header-rows: 1

   * - ``found`` / ``detail``
     - 의미
     - fail-open (데모)
     - fail-closed (실기)
   * - true (``""`` · ``stub``)
     - 보임
     - 진행
     - 진행
   * - false, ``""``
     - 안 보임
     - 중단 · "~가 보이지 않습니다"
     - ``precheck_timeout_s`` 동안 재확인 → 중단
   * - false, ``no_frame`` · ``stale`` · ``insufficient_frames`` · ``model_not_loaded`` ·
       ``inference_error`` · ``no_detector`` · ``detector_timeout`` · ``detector_error``
     - 판정 불가
     - 진행
     - 재확인 → 중단 · "~의 존재를 확인할 수 없어 작업을 중단합니다"
   * - false, ``unknown_target`` · ``unsupported_class`` · ``invalid_request``
     - 설정 오류
     - 진행
     - 재확인 없이 즉시 중단

재확인할 때마다 모든 대상을 다시 묻는다 — 앞서 한 대상만 보였던 결과를 이어 붙이지 않는다.
사전 확인 중에 "그만" 이 오면 Cmd 를 보내기 전이므로 cancel 없이 바로 멈춘다.

**4. 프로필**

.. list-table::
   :widths: 30 32 38
   :header-rows: 1

   * -
     - 데모 (``llm_demo.launch.py``)
     - 실기 (``cortex.launch.py`` · ``cortex_params.yaml``)
   * - detector
     - ``always`` 스텁 (가중치 불필요)
     - ``yolo`` · ``/models/cortex/yolo26s_fridge_cucumber_continued.pt`` (SHA-256 고정, 없으면 기동 실패)
   * - 신뢰도 기준
     - —
     - 0.25
   * - ``detector_fail_open``
     - true
     - false
   * - ``precheck_timeout_s`` / ``precheck_retry_s``
     - 0 (한 번만)
     - 1.0 s / 0.1 s

cortex 도커 이미지에 CUDA PyTorch · ultralytics 가 들어 있다. 실기는 ``docker/run.sh`` 가 GPU 를
열고 호스트 ``~/models/cortex`` 를 ``/models/cortex`` 로 읽기 전용 마운트한다 (``CORTEX_GPUS`` ·
``CORTEX_MODEL_DIR``). 자세한 것은 cortex ``docs/yolo_deployment.md``.

**5. 한계**

- ``fridge_door`` 는 ``refrigerator`` 클래스의 **존재** 만 본다. 문이 열렸는지, 닿을 수 있는지는 판정하지 않는다.
- 2 클래스 가중치(냉장고 · 오이)에는 ``person`` 이 없어 ``user`` 는 ``unsupported_class`` 다 —
  실기 프로필에서 **handover 는 막힌다.**
- 실행 후 확인(문 열림 · 그리퍼의 오이)은 없다.
<<<

[ICD]
UID: ICD-70
TITLE: Subtask Cmd (orchestrator → nav-planner)
COMM_TYPE: DDS Topic
SOURCE: orchestrator_node
TARGET: nav-planner
TOPIC: rt/cortex/nav/cmd
MSG_TYPE: cortex_msgs::msg::dds_::SubtaskCmd_
QOS: Reliable
FREQUENCY: 이벤트 (subtask 1건마다 1회)
STATEMENT: >>>
``plan_id`` (``p-<오케스트레이터 시작 epoch>-<4자리 일련>``) + ``index`` (계획 내 순번, 0부터)
+ ``action`` + ``args`` (서명 순서) + ``instruction`` (VLA 전용, nav 는 빈 문자열)
+ ``cancel`` (true 면 해당 ``plan_id``/``index`` 를 취소하고 나머지 필드는 무시).

nav 는 ``action`` 이 ``move_to`` 인 것만 처리하고, ``args[0]`` 을 ``config/destinations.yaml``
의 목적지 이름으로 해석한다. 그 밖의 action 은 ``unsupported`` 로 FAILED 를 돌려준다.

송신 · 판정 · 취소 규칙은 이 섹션 머리의 **Subtask 실행 규약** (``RULE-SUBTASK``) 을 따른다.
<<<
PRECONDITION: nav-planner 가 목적지 카탈로그를 적재한 상태
COMMENT: >>>
양측 구현 완료 (cortex ``743ce11`` / navigation-planner ``0a31cf9``, 2026-09-26).
이전의 ``(미정) ActionCmd`` 를 이 계약으로 대체하였다.

2026-10-03 (cortex #27): Cmd 는 마지막 보고가 IDLE 인 모듈에만 보낸다 — Cmd 로 하는 선점을 없앴다
(VLA 측 요청). 응답 없는 cancel 은 1회 재전송한다.

송신 규칙 1·2 는 cortex ``03b6e1d`` (#20, 2026-09-28). 같은 커밋이 취소 경로의 결함도
고쳤다 — ``SubtaskCmd`` 에서 ``header`` 를 뺀 뒤에도 취소 송신이 ``header`` 를 채우려 해,
그 사이 main 에서는 **취소를 보내는 순간 orchestrator_node 가 종료되었다**
(``743ce11`` ~ ``03b6e1d``). 모듈 쪽은 바꿀 것이 없다.

**DDS 이름 정합이 이 인터페이스의 핵심 위험이다.** 오케스트레이터가 ROS 2 노드이므로
와이어에 올라가는 이름은 변형된 형태(``rt/`` 접두사, ``::msg::dds_::`` + 뒤 밑줄)이고,
DDS 는 토픽 이름과 타입 이름이 **함께** 맞아야 엔드포인트를 연결한다. 하나라도 어긋나면
오류 없이 **양측이 서로를 보지 못한다**. 세 레포가 각자 계약을 적어 두어 실제로 어긋나 있었고
2026-09-26 에 맞췄다. 실기 빌드로 확인하는 것이 남았다.
<<<
RELATIONS:
- TYPE: Parent
  VALUE: SYS-REQ-44
  ROLE: Implements
- TYPE: Parent
  VALUE: SYS-REQ-45
  ROLE: Implements
- TYPE: File
  VALUE: _src/cortex/src/cortex_cognition/cortex_cognition/orchestrator_node.py
- TYPE: File
  VALUE: _src/cortex/src/cortex_msgs/msg/SubtaskCmd.msg
- TYPE: File
  VALUE: _src/cortex/src/cortex_cognition/cortex_cognition/executor.py
- TYPE: File
  VALUE: _src/navigation-planner/idl/kist_nav.idl
- TYPE: File
  VALUE: _src/navigation-planner/src/goal_generation/goal_command_receiver.cpp

[ICD]
UID: ICD-74
TITLE: Subtask State (nav-planner → orchestrator)
COMM_TYPE: DDS Topic
SOURCE: nav-planner
TARGET: orchestrator_node
TOPIC: rt/cortex/nav/state
MSG_TYPE: cortex_msgs::msg::dds_::SubtaskState_
QOS: Reliable
FREQUENCY: 10 Hz 상시 (IDLE 포함)
STATEMENT: >>>
``stamp_ns`` (발행 시각, epoch ns — 신선도 판정) + ``plan_id`` / ``index`` / ``action`` 되돌림
+ ``status`` (0 IDLE · 1 RUNNING · 2 DONE · 3 FAILED) + ``progress`` (0~1, 디버그용)
+ ``detail`` (사람이 읽는 사유. ``cancelled`` · ``unsupported: …`` · ``no path`` 등).

상태 전이 · 발행 규칙은 이 섹션 머리의 **Subtask 실행 규약** (``RULE-SUBTASK``) 을 따른다.
멈추는 동안에는 ``RUNNING`` 을 계속 보내다가 다 멈추면 ``IDLE`` (``detail`` ``cancelled``) 을
보낸다 — 별도의 STOPPING 상태는 없다.
<<<
PRECONDITION: nav-planner 기동
COMMENT: >>>
양측 구현 완료 (2026-09-26). ``progress`` 는 nav 에서 ``1 - 남은거리/초기거리`` 로 채운다.

이전에는 ``Header`` 를 쓰고 사유 필드를 ``note`` 로 불렀다. cortex · vla 와 맞추어
``stamp_ns`` · ``detail`` 로 통일했다 (navigation-planner ``0a31cf9``).

DONE · FAILED 3회 발행 뒤 IDLE 복귀를 구현했다 (navigation-planner ``12da99d``) — 규약 1 · 2 절과 일치.
<<<
RELATIONS:
- TYPE: Parent
  VALUE: SYS-REQ-45
  ROLE: Implements
- TYPE: Parent
  VALUE: SYS-REQ-44
  ROLE: Implements
- TYPE: File
  VALUE: _src/navigation-planner/src/controller/subtask_state_publisher.cpp
- TYPE: File
  VALUE: _src/navigation-planner/src/controller/controller_worker.cpp
- TYPE: File
  VALUE: _src/navigation-planner/idl/kist_nav.idl
- TYPE: File
  VALUE: _src/cortex/src/cortex_msgs/msg/SubtaskState.msg
- TYPE: File
  VALUE: _src/cortex/src/cortex_cognition/cortex_cognition/orchestrator_node.py

[ICD]
UID: ICD-75
TITLE: Subtask Cmd (orchestrator → vla-inference)
COMM_TYPE: DDS Topic
SOURCE: orchestrator_node
TARGET: vla-inference
TOPIC: rt/cortex/vla/cmd
MSG_TYPE: cortex_msgs::msg::dds_::SubtaskCmd_
QOS: Reliable
FREQUENCY: 이벤트 (subtask 1건마다 1회)
STATEMENT: >>>
ICD-70 과 같은 타입이다. VLA 는 ``move_to`` 를 제외한 19개 action 을 처리하며,
``instruction`` 에 영어 지시문이 함께 온다. 지시문은 ``config/vla_prompts.yaml`` 의 VLA 학습 문장을
먼저 쓰고, 없으면 ``config/actions.yaml`` 의 템플릿으로 만든다 (예 ``Hand the cucumber to the person.``).

LLM 계획에 없는 동작이 끼어 나갈 수 있다 (``config/plan_rewrites.yaml``):

- ``open`` 자동 삽입 (cortex #38): 문이 있는 곳(냉장고 · 찬장)에서 ``take_out`` · ``pick`` 하기 전에
  그 문을 여는 줄이 없으면 ``open(<문>)`` 을 넣고 "냉장고 문을 엽니다." 라고 말한다.
- 시연 보정 (cortex #21): ``open(fridge_door)`` 과 ``pick`` · ``take_out`` 사이의 ``approach``,
  ``pick`` · ``take_out`` 과 ``close(fridge_door)`` 사이의 ``step_back``. 말하지 않는다.

``instruction`` 은 VLA 학습 문장과 글자까지 같아야 한다 — 문장 목록은 **Subtask 실행 규약**
7 절. 빈 ``instruction`` 은 ``unsupported`` 로 FAILED 다. 송신 · 판정 · 취소 규칙도 같은 규약을 따른다.
<<<
PRECONDITION: vla-inference 정책 적재 완료
COMMENT: >>>
양측 구현 완료 (2026-09-26).

2026-09-28 (cortex ``03b6e1d``, #20) 부터 오케스트레이터가 VLA 에도 취소를 **즉시** 보낸다.
이전에는 오케스트레이터가 스스로 "안전 지점까지 대기" 를 구현해 VLA 에 취소를 아예 보내지
않았고, VLA 는 멈춰야 한다는 사실을 몰랐다. 지연 여부는 이제 모듈이 정한다.
현재 vla-inference 는 취소를 다음 추론 주기(~0.5 s) 안에 바로 반영한다
(``cancel_deferred`` 를 쓰지 않음).
<<<
RELATIONS:
- TYPE: Parent
  VALUE: SYS-REQ-31
  ROLE: Implements
- TYPE: Parent
  VALUE: SYS-REQ-44
  ROLE: Implements
- TYPE: File
  VALUE: _src/cortex/src/cortex_cognition/cortex_cognition/executor.py
- TYPE: File
  VALUE: _src/cortex/src/cortex_msgs/msg/SubtaskCmd.msg
- TYPE: File
  VALUE: _src/cortex/src/cortex_cognition/config/vla_prompts.yaml
- TYPE: File
  VALUE: _src/cortex/src/cortex_cognition/cortex_cognition/planner.py
- TYPE: File
  VALUE: _src/vla-inference/idl/cortex_subtask.idl
- TYPE: File
  VALUE: _src/vla-inference/src/vla/cortex/bridge.py
- TYPE: File
  VALUE: _src/vla-inference/src/vla/cortex/subtask_machine.py
- TYPE: File
  VALUE: _src/vla-inference/src/vla/progress_probe/probe_bank.py

[ICD]
UID: ICD-76
TITLE: Subtask State (vla-inference → orchestrator)
COMM_TYPE: DDS Topic
SOURCE: vla-inference
TARGET: orchestrator_node
TOPIC: rt/cortex/vla/state
MSG_TYPE: cortex_msgs::msg::dds_::SubtaskState_
QOS: Reliable
FREQUENCY: 10 Hz 상시 (IDLE 포함)
STATEMENT: >>>
``stamp_ns`` (발행 시각, epoch ns — 신선도 판정) + ``plan_id`` / ``index`` / ``action`` 되돌림
+ ``status`` (0 IDLE · 1 RUNNING · 2 DONE · 3 FAILED) + ``progress`` (0~1, 디버그용)
+ ``detail`` (사람이 읽는 사유. ``cancelled`` · ``unsupported: …`` · ``timeout …`` 등).

상태 전이 · 발행 규칙은 이 섹션 머리의 **Subtask 실행 규약** (``RULE-SUBTASK``) 을 따른다.
<<<
PRECONDITION: vla-inference 기동
COMMENT: >>>
양측 구현 완료 (2026-09-26). VLA 의 ``progress`` 는 추정값이라 판정에 쓰지 않는다 —
성공 여부는 ``status`` 만으로 판단한다.

2026-10-04 진행도 판정이 vla-inference main 에 들어왔다 (#5):

- **DONE**: 진행도 ≥ 0.70 이면 바로 DONE (``detail`` ``done (progress N.NN)``).
- **FAILED**: 시작 10 s 뒤부터 진행도 < 0.55 · 기울기 < 0.027/s 가 3 s 이어지면
  ``stalled at N.NN``. 임계값은 ``run_vla.py`` 플래그.
- DONE · FAILED 3회 뒤 IDLE, ``progress`` 필드에 진행도를 채운다. RUNNING 중 Cmd 는 무시한다
  (규약 1 절과 일치).
- 진행도 헤드는 ``instruction`` 과 글자까지 같은 학습 문장의 것만 쓰인다 — 문장이 다르면 DONE 이
  없고 단계 타임아웃(30 s)으로 끝난다 (규약 7 절 — 2026-10-15 기준 step_back · close · place ·
  handover 미기입).
- 가장 이른 정체 판정이 13 s 뒤라, 동작이 길면 오케스트레이터 단계 타임아웃(30 s)을 실측 후 늘려야 할 수 있다.
<<<
RELATIONS:
- TYPE: Parent
  VALUE: SYS-REQ-31
  ROLE: Implements
- TYPE: Parent
  VALUE: SYS-REQ-44
  ROLE: Implements
- TYPE: File
  VALUE: _src/vla-inference/src/vla/cortex/bridge.py
- TYPE: File
  VALUE: _src/vla-inference/src/vla/cortex/subtask_machine.py
- TYPE: File
  VALUE: _src/vla-inference/src/vla/progress_probe/progress_state.py
- TYPE: File
  VALUE: _src/vla-inference/src/common/cyclonedds/cortex_msgs.py
- TYPE: File
  VALUE: _src/cortex/src/cortex_msgs/msg/SubtaskState.msg
- TYPE: File
  VALUE: _src/cortex/src/cortex_cognition/cortex_cognition/orchestrator_node.py

[ICD]
UID: ICD-77
TITLE: Plan Request (orchestrator → llm)
COMM_TYPE: DDS Topic
SOURCE: orchestrator_node
TARGET: llm_node
TOPIC: /cortex/llm/request
MSG_TYPE: cortex_msgs/PlanRequest
QOS: Reliable
FREQUENCY: 이벤트 (발화 1건마다 1회)
STATEMENT: >>>
``plan_id`` + ``utterance`` (STT 원문) + ``state`` (``idle`` · ``running:<동사>`` ·
``awaiting_confirm:<요약>``) + ``at`` + ``holding``.

``at`` 은 마지막으로 도착에 성공한 장소(초기값 ``home``), ``holding`` 은 지금 들고 있는
물건(초기값 ``none``) 이다. 이 둘이 없으면 "테이블에 놔" 같은 연속 발화를 해석할 수 없다.
<<<
PRECONDITION: llm_node 기동 및 API 키 설정
COMMENT: >>>
오케스트레이터는 ``at`` · ``holding`` 을 명령 발행 시점이 아니라 **모듈이 돌려준 결과**\ 로
갱신한다. 이동 성공이면 ``at`` 을 바꾸고 실패면 ``unknown`` 으로 되돌리며, 놓기에 실패하면
물건이 아직 손에 있으므로 ``holding`` 을 유지한다.
<<<
RELATIONS:
- TYPE: Parent
  VALUE: SYS-REQ-44
  ROLE: Implements
- TYPE: File
  VALUE: _src/cortex/src/cortex_cognition/cortex_cognition/orchestrator_node.py
- TYPE: File
  VALUE: _src/cortex/src/cortex_cognition/cortex_cognition/llm_node.py
- TYPE: File
  VALUE: _src/cortex/src/cortex_msgs/msg/PlanRequest.msg

[ICD]
UID: ICD-78
TITLE: Plan Step (llm → orchestrator)
COMM_TYPE: DDS Topic
SOURCE: llm_node
TARGET: orchestrator_node
TOPIC: /cortex/llm/step
MSG_TYPE: cortex_msgs/PlanStep
QOS: Reliable
FREQUENCY: 스트리밍 (LLM 출력 1줄마다 1건)
STATEMENT: >>>
``kind`` (0 SUB · 1 END · 2 REPLY · 3 ERROR) + ``index`` + ``action`` + ``args``
+ ``say`` (시작할 때 로봇이 말할 한 문장) + ``reply_kind`` (``chat`` · ``none`` · ``confirm``)
+ ``detail``.

LLM 이 NDJSON 한 줄을 완성할 때마다 1건 발행한다. 오케스트레이터는 ``END`` 를 기다리지 않고
``index`` 0 이 도착하는 즉시 실행을 시작한다.
<<<
PRECONDITION: PlanRequest 수신
COMMENT: >>>
줄은 두 검증기를 통과한 것만 나간다. 검증기 1 은 형식(JSON · 아는 동사 · 인자 개수 ·
소문자 snake_case · 서명의 인자 이름을 값으로 쓰지 않았는지), 검증기 2 는 실행 가능성
(별칭 정규화 후 갈 수 있는 곳인지 · 다룰 수 있는 물건인지) 을 본다.

검증기 2 가 막으면 ``kind`` ``ERROR`` 로 사유 키를 실어 보내고, 오케스트레이터가 그것을
한국어 안내로 바꿔 말한다. 장소가 아닌 대상에 붙은 ``move_to`` 는 그 줄만 버리고 계획을
잇는다 (이때 ``index`` 를 다시 매긴다).
<<<
RELATIONS:
- TYPE: Parent
  VALUE: SYS-REQ-44
  ROLE: Implements
- TYPE: File
  VALUE: _src/cortex/src/cortex_cognition/cortex_cognition/llm_node.py
- TYPE: File
  VALUE: _src/cortex/src/cortex_cognition/cortex_cognition/planner.py
- TYPE: File
  VALUE: _src/cortex/src/cortex_cognition/cortex_cognition/orchestrator_node.py
- TYPE: File
  VALUE: _src/cortex/src/cortex_msgs/msg/PlanStep.msg

[ICD]
UID: ICD-79
TITLE: Target Check (orchestrator → detector)
COMM_TYPE: Call
SOURCE: orchestrator_node
TARGET: detector_node
TOPIC: /cortex/detector/check
MSG_TYPE: cortex_msgs/CheckTarget
QOS: Reliable
FREQUENCY: 이벤트 (조작 subtask 직전, 대상마다 1회 · 재확인 시 0.1 s 간격)
STATEMENT: >>>
요청 ``target`` (어휘 키, + ``min_confidence`` · ``max_age_s``, 0 이면 검출기 기본값) /
응답 ``found`` · ``confidence`` · ``label`` (YOLO 클래스) · bbox (``cx`` ``cy`` ``w`` ``h``, 0~1 정규화)
· ``stamp`` (검출된 프레임의 영상 원본 시각, 못 찾으면 0) · ``detail``.

``detail``: ``""`` (보통 판정) · ``stub`` (데모 스텁) · ``no_frame`` · ``stale`` · ``insufficient_frames`` ·
``unknown_target`` · ``unsupported_class`` · ``model_not_loaded`` · ``inference_error`` · ``invalid_request``.
오케스트레이터 쪽에서 붙는 ``no_detector`` · ``detector_timeout`` · ``detector_error`` 도 같은 칸에 실린다.

새로 추론하지 않고 최근 창에서 답하므로 빨리 돌아온다. 판정 기준과 결과별 동작은 이 섹션 머리의
**사전 확인 규약** (``RULE-PRECHECK``) 을 따른다.
<<<
PRECONDITION: detector_node 기동 (실기 프로필은 가중치 파일 필요)
COMMENT: >>>
2026-10-05 YOLO 연동이 main 에 들어왔다 (cortex #29, 황재영). 실기 기본값(``cortex_params.yaml``)이
``backend: yolo`` · fail-closed 로 바뀌었고, 데모(``llm_demo.launch.py``)만 ``always`` 스텁 · fail-open 이다.
이전 정책 "안 보임일 때만 중단, 판정 불가는 진행" 은 데모 프로필에만 남았다.

대상 키 → YOLO 클래스: ``fridge_door`` · ``fridge`` → ``refrigerator``, ``cucumber`` → ``cucumber``,
``user`` → ``person`` (현재 가중치에 없어 ``unsupported_class``).
<<<
RELATIONS:
- TYPE: Parent
  VALUE: SYS-REQ-44
  ROLE: Implements
- TYPE: File
  VALUE: _src/cortex/src/cortex_cognition/cortex_cognition/orchestrator_node.py
- TYPE: File
  VALUE: _src/cortex/src/cortex_cognition/cortex_cognition/executor.py
- TYPE: File
  VALUE: _src/cortex/src/cortex_cognition/cortex_cognition/planner.py
- TYPE: File
  VALUE: _src/cortex/src/cortex_cognition/config/actions.yaml
- TYPE: File
  VALUE: _src/cortex/src/cortex_perception/cortex_perception/detector_node.py
- TYPE: File
  VALUE: _src/cortex/src/cortex_perception/cortex_perception/detection.py
- TYPE: File
  VALUE: _src/cortex/src/cortex_msgs/srv/CheckTarget.srv
- TYPE: File
  VALUE: _src/cortex/src/cortex_bringup/config/cortex_params.yaml

[ICD]
UID: ICD-81
TITLE: LLM API (llm_node → Gemini)
COMM_TYPE: HTTPS
SOURCE: llm_node
TARGET: Gemini API
MSG_TYPE: google-genai streaming
QOS: N/A
FREQUENCY: 이벤트 (발화 1건마다 1회)
STATEMENT: >>>
시스템 프롬프트(``config/actions.yaml`` 에서 생성) + 사용자 메시지(``mode`` · ``at`` ·
``holding`` · ``utterance``) 를 보내고 NDJSON 스트림을 받는다. 모델 ``gemini-3.6-flash``.
<<<
PRECONDITION: GOOGLE_API_KEY 환경변수
COMMENT: >>>
백엔드는 ``dummy`` 가 기본이고 실행할 때 고른다 (예 ``llm_demo.launch.py backend:=gemini``).
첫 줄 도착 5초 · 전체 20초 타임아웃이고 (코드 기본값 15초를 ``cortex_params.yaml`` 이 20초로 덮어쓴다),
실패하면 1회 재시도한다. **재시도는 아직 아무
줄도 내보내지 않은 경우에만 안전하다** — 이미 내보낸 뒤면 계획이 섞인다.

측정에서 응답이 오지 않는 요청 하나에 73분 매달린 적이 있어 넣은 장치다. 실측 첫 줄
p50 1.57초 · p95 1.93초 (108발화 × 5회).
<<<
RELATIONS:
- TYPE: Parent
  VALUE: SYS-REQ-44
  ROLE: Implements
- TYPE: File
  VALUE: _src/cortex/src/cortex_cognition/cortex_cognition/llm_node.py
- TYPE: File
  VALUE: _src/cortex/src/cortex_cognition/cortex_cognition/planner.py
- TYPE: File
  VALUE: _src/cortex/src/cortex_cognition/config/actions.yaml

[ICD]
UID: ICD-82
TITLE: Nav Destinations (nav-planner → peers)
COMM_TYPE: DDS Topic
SOURCE: nav-planner
TARGET: orchestrator_node
TOPIC: rt/kist/nav/destinations
MSG_TYPE: kist_msgs::NavDestinationList
QOS: Reliable
FREQUENCY: 저주기 재발행 (늦게 붙은 구독자용)
STATEMENT: >>>
``seq`` + ``stamp_ns`` + ``destinations`` (각 항목은 ``name`` · ``x`` · ``y`` · ``yaw_deg``).
``config/destinations.yaml`` 을 그대로 실어 보낸다 — 갈 수 있는 곳의 목록이다.
<<<
PRECONDITION: nav-planner 기동
COMMENT: >>>
⚠ **오케스트레이터는 이 토픽을 구독하지 않기로 결정했다** (2026-09-26). 계약을
``cmd`` / ``state`` 두 토픽으로 유지하기 위해서다. 모듈마다 전용 타입이 늘면 계약이
비대칭해지고, 같은 판단이 두 곳에 생겨 언젠가 어긋난다.

대신 cortex 는 ``config/capabilities.yaml`` 의 ``nav.places`` 를 **손으로 유지하는 설정**\ 으로
둔다. 그것은 빠른 사전 차단일 뿐 최종 권한이 아니며, 목록이 낡아 통과한 줄은 nav 이
``FAILED`` 로 돌려준다. **station 이 바뀌면 두 파일을 같이 고쳐야 한다.**
<<<
RELATIONS:
- TYPE: Parent
  VALUE: SYS-REQ-45
  ROLE: Implements
- TYPE: File
  VALUE: _src/navigation-planner/src/goal_generation/destination_publisher.cpp
- TYPE: File
  VALUE: _src/navigation-planner/config/destinations.yaml
- TYPE: File
  VALUE: _src/cortex/src/cortex_cognition/config/capabilities.yaml

[ICD]
UID: ICD-84
TITLE: Detections (detector → peers)
COMM_TYPE: DDS Topic
SOURCE: detector_node
TARGET: Cortex
TOPIC: /cortex/detections
MSG_TYPE: cortex_msgs/DetectionArray
QOS: BestEffort
FREQUENCY: 8 Hz
STATEMENT: >>>
``Detection`` 배열 (``label`` · ``confidence`` · bbox) + ``model`` · ``infer_ms``. 최근 추론 결과를
그대로 공개한다. ``header`` 의 시각 · ``frame_id`` 는 추론한 영상 프레임의 원본 값이다.
실기 프로필(``backend: yolo``)에서만 나온다.
<<<
PRECONDITION: detector_node 기동
COMMENT: >>>
⚠ **수신측 미구현.** 판정은 ICD-79 의 서비스로 하므로 이 토픽을 쓰는 곳이 아직 없다.
디버그·시각화용으로 남겨 두었다.
<<<
RELATIONS:
- TYPE: Parent
  VALUE: SYS-REQ-44
  ROLE: Implements
- TYPE: File
  VALUE: _src/cortex/src/cortex_perception/cortex_perception/detector_node.py
- TYPE: File
  VALUE: _src/cortex/src/cortex_msgs/msg/DetectionArray.msg
- TYPE: File
  VALUE: _src/cortex/src/cortex_msgs/msg/Detection.msg

[ICD]
UID: ICD-72
TITLE: Nav Cmd Vel (nav-planner → gearsonic)
COMM_TYPE: DDS Topic
SOURCE: nav-planner
TARGET: gearsonic
TOPIC: rt/kist/nav/cmd_vel
MSG_TYPE: geometry_msgs::msg::dds_::Twist_
QOS: N/A
FREQUENCY: ~20 Hz (계획 주기)
STATEMENT: >>>
``linear.x = vx``, ``linear.y = vy``, ``angular.z = vyaw`` — base 좌표계 속도 명령.
gearsonic의 ``NavCmdReceiver`` 가 수신해 ``InputHandler::nav_buf`` 에 넣고, 조종기 스틱이 중립일 때
플래너 setpoint로 쓴다. NaN/Inf 명령은 거부한다. vx·vy를 모두 소비하므로 옆걸음을 지원한다.
<<<
PRECONDITION: gearsonic 실행 + 스틱 중립 + E-STOP 미발효
COMMENT: >>>
양측 구현 완료. navigation-planner 의 ``NavCommandPublisher`` 가 Unitree ``ChannelPublisher`` 로
``geometry_msgs::msg::dds_::Twist_`` 를 발행하고 (``linear.z`` · ``angular.x/y`` 는 0), 종료할 때 0 속도를
한 번 보내 멈춘다. gearsonic 수신부는 ``0c5f8d3`` 에서 먼저 들어왔다. QoS 는 ``ChannelPublisher`` 기본값이다.
이 인터페이스로 nav-planner → gearsonic 경로는 in-process 라이브러리 호출이 아니라 DDS 토픽이다.
<<<
RELATIONS:
- TYPE: Parent
  VALUE: SYS-REQ-45
  ROLE: Implements
- TYPE: File
  VALUE: _src/navigation-planner/src/controller/nav_command_publisher.cpp
- TYPE: File
  VALUE: _src/navigation-planner/include/controller/nav_command_publisher.hpp
- TYPE: File
  VALUE: _src/gearsonic-inference/src/motion/nav_cmd_receiver.cpp
- TYPE: File
  VALUE: _src/gearsonic-inference/include/motion/nav_cmd_receiver.hpp
- TYPE: File
  VALUE: _src/gearsonic-inference/src/motion/input_handler.cpp

[[/SECTION]]

[[SECTION]]
TITLE: 모니터링 및 디스플레이

[TEXT]
STATEMENT: >>>
카메라 영상과 태스크 상태를 외부 디스플레이로 내보내는 경로이다. ``SYS-REQ-41`` / ``SYS-REQ-49`` 를 구현한다.
<<<

[TEXT]
STATEMENT: >>>
.. gen_arch: 아래 흐름도는 tools/gen_arch.py 가 이 섹션의 ICD 노드에서 생성한다. 직접 편집하지 말 것.

.. raw:: html

   <div style="overflow-x:auto; max-width:100%;">
   <pre class="mermaid">
      flowchart TB
        subgraph onboard["Unitree G1 (NX) — Onboard"]
          n_ext_sensor_io["ext-sensor-io"]
        end
        subgraph workstation["PC (RTX 4090) — Workstation"]
          n_orchestrator_node["orchestrator_node"]
          n_detector_node["detector_node"]
          n_gui_bridge_node["gui_bridge_node"]
          n_Cortex["Cortex"]
        end
        subgraph external["External"]
          n_Display_Renderer["Display Renderer"]
        end
        n_session_recorder_node["session_recorder_node (구역 미지정)"]

        n_ext_sensor_io -->|"ICD-62"| n_detector_node
        n_orchestrator_node -->|"ICD-67"| n_gui_bridge_node
        n_orchestrator_node -->|"ICD-80"| n_gui_bridge_node
        n_Cortex -->|"ICD-87"| n_session_recorder_node
        n_gui_bridge_node -.->|"ICD-55"| n_Display_Renderer
   </pre>
   </div>
<<<

[ICD]
UID: ICD-62
TITLE: Camera Color (ext-sensor → PC)
COMM_TYPE: DDS Topic
SOURCE: ext-sensor-io
TARGET: detector_node
TOPIC: rt/kist/camera/<name>/color/h264
MSG_TYPE: kist_msgs::msg::dds_::CompressedColorFrame_
QOS: BestEffort
FREQUENCY: 30 Hz
STATEMENT: >>>
H.264 NAL + ``seq`` / ``stamp`` / ``width`` / ``height`` / ``keyframe``.
카메라 이름(``head`` / 양 손목)별 토픽.

소비처: detector_node(대상 확인) · gui_bridge_node(표시) · vla-inference(정책 관측).

cortex 는 ROS 메시지 ``kist_msgs/CompressedColorFrame`` 으로 ``/kist/camera/head/color/h264`` 를 구독해
PyAV 로 디코드한다. gui_bridge 는 최신 프레임만 JPEG 로 (≤ 15 Hz) 내보낸다. detector 는 실기
프로필(``backend: yolo``)에서 best-effort · depth 1 로 구독해 프레임 원본 시각을 유지하고, 데모
(``always`` 스텁)에서는 구독하지 않는다.
<<<
PRECONDITION: ext-sensor tx(카메라) 활성
COMMENT: >>>
TARGET 은 대표 소비처(detector_node)만 표기. 실제 소비처는 File 관계 참조.
navigation-planner 의 세그멘테이션 소비부는 LIO 재구성 때 ``_parked/`` 로 보류되었다가
레포에서 삭제되었다 (navigation-planner ``b44f6d7``).

2026-09-28: 타입 이름을 ``kist_msgs::CompressedColorFrame`` 에서 ROS 2 형식으로 바꿨다
(ext-sensor-io ``48c6ca9`` #3 · vla-inference ``e6c4af8`` #3 · cortex ``728a492`` #23, 같이 머지).
<<<
RELATIONS:
- TYPE: Parent
  VALUE: SYS-REQ-42
  ROLE: Implements
- TYPE: Parent
  VALUE: SYS-REQ-41
  ROLE: Implements
- TYPE: Parent
  VALUE: SYS-REQ-31
  ROLE: Implements
- TYPE: File
  VALUE: _src/ext-sensor-io/src/realsense/transmitter/color_publisher.cpp
- TYPE: File
  VALUE: _src/ext-sensor-io/src/realsense/transmitter/h264_encoder.cpp
- TYPE: File
  VALUE: _src/cortex/src/cortex_perception/cortex_perception/detector_node.py
- TYPE: File
  VALUE: _src/cortex/src/cortex_gui/cortex_gui/gui_bridge_node.py
- TYPE: File
  VALUE: _src/vla-inference/src/vla/io/realsense/color_subscriber.py
- TYPE: File
  VALUE: _src/cortex/src/cortex_perception/cortex_perception/ext_sensor.py
- TYPE: File
  VALUE: _src/cortex/src/kist_msgs/msg/CompressedColorFrame.msg
- TYPE: File
  VALUE: _src/ext-sensor-io/idl/kist_camera_frames.idl

[ICD]
UID: ICD-67
TITLE: Task Status (orchestrator → gui_bridge)
COMM_TYPE: DDS Topic
SOURCE: orchestrator_node
TARGET: gui_bridge_node
TOPIC: /cortex/task_status
MSG_TYPE: cortex_msgs/TaskStatus
QOS: Reliable
FREQUENCY: 상태 변화 시
STATEMENT: >>>
``header`` + ``task_name`` + ``current_subtask`` + ``subtask_index`` (0-based)
+ ``subtask_count`` + ``state`` (IDLE / RUNNING / SUCCEEDED / FAILED / PREEMPTED) + ``detail``.

open-loop 상태머신에서는 IDLE ↔ RUNNING 만 사용한다.
<<<
PRECONDITION: orchestrator 실행 중
RELATIONS:
- TYPE: Parent
  VALUE: SYS-REQ-41
  ROLE: Implements
- TYPE: File
  VALUE: _src/cortex/src/cortex_cognition/cortex_cognition/orchestrator_node.py
- TYPE: File
  VALUE: _src/cortex/src/cortex_gui/cortex_gui/gui_bridge_node.py
- TYPE: File
  VALUE: _src/cortex/src/cortex_msgs/msg/TaskStatus.msg

[ICD]
UID: ICD-80
TITLE: Trace Event (orchestrator → gui_bridge)
COMM_TYPE: DDS Topic
SOURCE: orchestrator_node
TARGET: gui_bridge_node
TOPIC: /cortex/trace
MSG_TYPE: cortex_msgs/TraceEvent
QOS: Reliable
FREQUENCY: 이벤트 (생각의 흐름 1건마다)
STATEMENT: >>>
``kind`` 12종 (HEARD · THINKING · PLAN_LINE · PLAN_END · REPLY · STEP_START · STEP_DONE ·
STEP_FAILED · GROUND · CANCEL · PLAN_DONE · NOTE) + ``index`` + ``title`` (화면에 그대로
쓰는 한국어) + 본문.

- ``NOTE`` 이고 ``index`` 가 -1 이면 계획을 세우지 못한 것이다. ``title`` 은 로봇이 실제로
  말한 문장이다 (예 검증기 2 가 막은 장소: "그곳은 아직 갈 수 없습니다.").
- ``CANCEL`` 의 ``title``: ``이동 취소`` · ``동작 취소`` (실행 중 단계에 cancel 송신),
  ``다음 단계 전에 중단`` (단계 사이의 멈춤), ``계획 중단`` (실패·타임아웃),
  ``현재 동작 완료 후 중단`` (계획 도중 LLM 오류).
<<<
PRECONDITION: gui_bridge_node 기동
COMMENT: >>>
gui_bridge 가 최근 이벤트를 고리 버퍼에 들고 있어, 늦게 접속한 화면에도 **지금 계획의
이벤트를 되돌려 보여준다**. 시연 중 브라우저를 새로 열어도 진행 상황이 비지 않는다.

``NOTE`` -1 의 문장은 cortex ``5859ffc`` (#18), ``CANCEL`` 제목은 ``03b6e1d`` (#20).
화면 표시는 cortex-gui ``28a184a`` (#5).
<<<
RELATIONS:
- TYPE: Parent
  VALUE: SYS-REQ-41
  ROLE: Implements
- TYPE: File
  VALUE: _src/cortex/src/cortex_cognition/cortex_cognition/orchestrator_node.py
- TYPE: File
  VALUE: _src/cortex/src/cortex_gui/cortex_gui/gui_bridge_node.py
- TYPE: File
  VALUE: _src/cortex/src/cortex_msgs/msg/TraceEvent.msg

[ICD]
UID: ICD-87
TITLE: Event Log (cortex nodes → session_recorder)
COMM_TYPE: DDS Topic
SOURCE: Cortex
TARGET: session_recorder_node
TOPIC: /cortex/events
MSG_TYPE: std_msgs/String
QOS: Reliable
FREQUENCY: 이벤트 (노드 이벤트 1건마다)
STATEMENT: >>>
cortex 노드들이 이벤트를 JSON 한 줄로 발행한다: ``stamp_ns`` · ``node`` · ``topic`` · ``event`` · ``fields``.
무엇을 보낼지는 ``config/logging.yaml`` 의 ``record`` (기본 ``all``) 로 정한다. 콘솔 출력(``events``)과는 따로다.

orchestrator 는 발화 명령 하나를 세션으로 보고 ``SESSION_START`` (``plan_id`` · 발화) 와
``SESSION_END`` (``outcome`` · ``detail`` · ``duration_s`` · ``steps``) 를 세션마다 한 번씩 낸다.
``outcome`` 은 ``succeeded`` · ``failed`` · ``stopped`` · ``preempted`` · ``reply`` · ``confirm`` ·
``plan_error`` · ``plan_timeout`` · ``replaced`` · ``dropped`` 중 하나다.

session_recorder_node 는 이를 세션별 파일로 저장한다. 시작 5초 전부터 종료 2초 뒤까지를
``~/cortex_logs/<날짜>/HHMMSS_<plan_id>.jsonl`` 에, 그날의 목록을 같은 폴더 ``sessions.csv`` 에 쓴다.
14일 지난 날짜 폴더는 지운다.
<<<
PRECONDITION: session_recorder_node 기동 (``logging.yaml`` ``session_log.enabled``)
COMMENT: >>>
기록 전용이다. 실행 판단에는 쓰지 않는다. 이벤트 · 세션 경계는 cortex #43, recorder 는 #44,
콘솔의 ``EVENT_NAME {json}`` 형식은 #40. Docker 에서는 ``docker/run.sh`` 가 호스트 ``~/cortex_logs`` 를
마운트하고 호스트 시간대를 공유한다. 운영 안내는 cortex ``docs/session_log.md``.
<<<
RELATIONS:
- TYPE: Parent
  VALUE: SYS-REQ-44
  ROLE: Implements
- TYPE: File
  VALUE: _src/cortex/src/cortex_common/cortex_common/events.py
- TYPE: File
  VALUE: _src/cortex/src/cortex_cognition/cortex_cognition/executor.py
- TYPE: File
  VALUE: _src/cortex/src/cortex_common/cortex_common/session_recorder_node.py
- TYPE: File
  VALUE: _src/cortex/src/cortex_common/cortex_common/session_log.py
- TYPE: File
  VALUE: _src/cortex/src/cortex_bringup/config/logging.yaml

[ICD]
UID: ICD-55
TITLE: GUI Status + Frame Stream (gui_bridge → Display Renderer)
COMM_TYPE: WebSocket
SOURCE: gui_bridge_node
TARGET: Display Renderer
TOPIC: ws://<cortex-host>:8081
MSG_TYPE: text = JSON status / binary = camera JPEG bytes
QOS: N/A
FREQUENCY: ~15 Hz
STATEMENT: >>>
**text, status (JSON, 구 계약 · 유지):**
``{scenario: str|null, subtask: {name: str, i: int, n: int}|null, state: 'idle|active|success|failed'}``

**text, event (JSON):** ICD-80 ``/cortex/trace`` 한 건마다 한 메시지.
``{type: 'event', t: float, plan_id: str, kind: str, index: int, title: str, body: str}``.
늦게 접속한 client 에는 지금 계획의 event 를 먼저 되돌려 보낸다.

**binary:** 최신 카메라 JPEG bytes (첫 프레임 전에는 생략).

매 tick 마다 각 client는 text → binary 순으로 수신한다.
latest-wins 백프레셔: 이전 broadcast 미완료 시 프레임을 drop 하고,
``send_timeout_s`` 초과 client는 연결을 끊는다.
<<<
PRECONDITION: >>>
gui_bridge_node 가 ``/cortex/task_status`` · ``/cortex/trace`` · ``/kist/camera/head/color/h264``
(ICD-62, H.264 → JPEG) 를 구독하여 WebSocket으로 재발행한다. 브라우저 Display Renderer(``cortex-gui``, app.js)는 ``?ws=`` 쿼리로
cortex 호스트를 지정한다. ROS 비의존, 단일 LAN, e2e ≤ 200 ms.
<<<
COMMENT: >>>
2026-06-06 de-scope — estop / STT / TTS 필드 제외. JSON 계약의 소유자는 렌더러(cortex-gui).

2026-09-28: 렌더러가 event 메시지로 생각의 흐름(HEARD · PLAN · NOW)을 그린다
(cortex-gui ``28a184a``, #5). 렌더러는 cortex 와 별도 컨테이너(``kist-cortex-gui``, :8080)로,
cortex 는 ``kist-cortex`` 컨테이너로 뜬다 (cortex-gui #6 · cortex #19). 계약 변화는 없다.
<<<
RELATIONS:
- TYPE: Parent
  VALUE: SYS-REQ-41
  ROLE: Implements
- TYPE: Parent
  VALUE: SYS-REQ-49
  ROLE: Implements
- TYPE: File
  VALUE: _src/cortex/src/cortex_gui/cortex_gui/gui_bridge_node.py
- TYPE: File
  VALUE: _src/cortex-gui/app.js

[[/SECTION]]

[[SECTION]]
TITLE: 센서 입력 (측위 · 인지)

[TEXT]
STATEMENT: >>>
로봇 측위와 환경 인지에 쓰이는 센서 스트림이다. 모두 navigation-planner가 소비한다.
``SYS-REQ-42`` (센서 수집) 와 ``SYS-REQ-45`` (자율 보행) 를 구현한다.
<<<

[TEXT]
STATEMENT: >>>
.. gen_arch: 아래 흐름도는 tools/gen_arch.py 가 이 섹션의 ICD 노드에서 생성한다. 직접 편집하지 말 것.

.. raw:: html

   <div style="overflow-x:auto; max-width:100%;">
   <pre class="mermaid">
      flowchart TB
        subgraph onboard["Unitree G1 (NX) — Onboard"]
          n_G1["G1"]
          n_ext_sensor_io["ext-sensor-io"]
        end
        subgraph workstation["PC (RTX 4090) — Workstation"]
          n_nav_planner["nav-planner"]
          n_FAST_LIO_engine["FAST-LIO engine"]
        end

        n_ext_sensor_io -->|"ICD-36"| n_nav_planner
        n_G1 -->|"ICD-58"| n_FAST_LIO_engine
        n_FAST_LIO_engine -->|"ICD-85"| n_nav_planner
        n_ext_sensor_io -->|"ICD-63"| n_nav_planner
   </pre>
   </div>
<<<

[ICD]
UID: ICD-36
TITLE: UWB Pose (ext-sensor → nav-planner)
COMM_TYPE: DDS Topic
SOURCE: ext-sensor-io
TARGET: nav-planner
TOPIC: rt/kist/uwb/pose
MSG_TYPE: geometry_msgs/PoseStamped
QOS: BestEffort
FREQUENCY: ~20 Hz
STATEMENT: >>>
``x``, ``y``, ``theta`` (map frame). navigation-planner의 PoseFilter가 오도메트리(ICD-58 경로의
``rt/dog_odom``)와 EKF 융합하여 로봇 위치를 추정한다.
<<<
PRECONDITION: UWB 모듈(DWM) 활성
COMMENT: Notion 원본은 소비처를 orchestrator(도착 판정, 미배선)로 두었으나 현재 실제 소비처는 navigation-planner이다.
RELATIONS:
- TYPE: Parent
  VALUE: SYS-REQ-42
  ROLE: Implements
- TYPE: Parent
  VALUE: SYS-REQ-45
  ROLE: Implements
- TYPE: File
  VALUE: _src/ext-sensor-io/src/uwb/transmitter/uwb_publisher.cpp
- TYPE: File
  VALUE: _src/ext-sensor-io/src/system/uwb_transmitter.cpp
- TYPE: File
  VALUE: _src/navigation-planner/src/localization/uwb_receiver.cpp
- TYPE: File
  VALUE: _src/navigation-planner/src/localization/localization_filter.cpp

[ICD]
UID: ICD-58
TITLE: LiDAR Raw Scan (G1 → FAST-LIO engine)
COMM_TYPE: DDS Topic
SOURCE: G1
TARGET: FAST-LIO engine
TOPIC: /livox/lidar
MSG_TYPE: livox_ros_driver2 (raw Livox packet)
QOS: BestEffort
FREQUENCY: 10 Hz (Mid-360)
STATEMENT: >>>
Livox Mid-360 의 원시 스캔을 deepglint 의 수정 ``livox_ros_driver2`` 가 로봇 LAN 에서 직접 읽어
``/livox/lidar`` 로 발행하고, 같은 엔진의 FAST-LIO 가 이를 소비한다.
라이다 IP ``192.168.123.120``, 호스트 ``192.168.123.222`` (``lio_engine/config/MID360_config.json``).
<<<
PRECONDITION: LIO 엔진 데몬 실행 (``run_lio_daemon``)
COMMENT: >>>
**이전에는 nav-planner 가 Unitree 의 ``rt/utlidar/cloud_livox_mid360`` 릴레이를 직접 구독했다.
그 경로는 폐기했다** — 릴레이의 클라우드가 직선 이동을 늘려 읽고 빠른 회전에서 겹침을 만들었다.
원시 Livox 데이터를 FAST-LIO 에 직접 넣으면 사라진다 (실기 검증: 정지 시 안정, 1.5 m 이동을
약 1.40 m 로 읽음, rviz 에서 벽이 고정).

엔진은 우리 코드가 아니다 — deepglint ``FAST_LIO_LOCALIZATION_HUMANOID`` 를 커밋 고정해
(``docker/Dockerfile`` 의 ARG) 빌드 시 받아 ``/opt/lio_ws`` 에 그대로 넣는다. 레포에 vendoring
하지 않는다. 따라서 이 인터페이스에는 우리 구현 파일이 없고, 설정과 문서만 있다.

엔진과 플래너는 **같은 이미지 안의 두 프로세스**\ 이며 localhost DDS 로만 통신한다
(FastDDS ↔ CycloneDDS RTPS interop, 검증됨). ROS 2 는 플래너 빌드에 들어오지 않는다.
<<<
RELATIONS:
- TYPE: Parent
  VALUE: SYS-REQ-45
  ROLE: Implements
- TYPE: Parent
  VALUE: SYS-REQ-42
  ROLE: Implements
- TYPE: File
  VALUE: _src/navigation-planner/lio_engine/config/MID360_config.json
- TYPE: File
  VALUE: _src/navigation-planner/lio_engine/config/mid360.yaml
- TYPE: File
  VALUE: _src/navigation-planner/docs/LIO_ENGINE.md

[ICD]
UID: ICD-85
TITLE: LIO Odometry + Registered Cloud (FAST-LIO engine → nav-planner)
COMM_TYPE: DDS Topic
SOURCE: FAST-LIO engine
TARGET: nav-planner
TOPIC: rt/Odometry_loc · rt/cloud_registered_1
MSG_TYPE: nav_msgs::msg::dds_::Odometry_ · sensor_msgs::msg::dds_::PointCloud2_
QOS: BestEffort
FREQUENCY: 10 Hz (스캔 주기)
STATEMENT: >>>
``rt/Odometry_loc`` 는 맵 좌표계의 라이다 pose (``T_odom_lidar``), ``rt/cloud_registered_1`` 은
그 pose 로 정합된 스캔이다. 플래너는 전자로 변환 체인의 뿌리를 세우고, 후자로 3D voxel
점유 격자와 costmap 을 만든다.

``mid360.yaml`` 의 ``dense_publish_en: false`` 이므로 정합 클라우드는 다운샘플된 스캔이다
(전체 약 2만 점이 필요하면 true).
<<<
PRECONDITION: LIO 엔진 데몬 실행, 사전 지도 적재
COMMENT: >>>
**플래너는 SLAM 을 직접 돌리지 않는다.** 이 두 토픽이 끊기면 플래너는 자기 위치를 모르므로
아무 목적지도 수행할 수 없다 — 실기에서 nav 이 움직이지 않을 때 가장 먼저 볼 곳이다.

두 프로세스가 같은 컨테이너의 localhost 에서만 통신하므로 네트워크 구성에는 드러나지 않는다.
ROS 2 쪽이 발행하므로 타입·토픽 이름이 ``rt/`` + ``::msg::dds_::`` 형태다.

2026-10-12 (navigation-planner ``098f198``, #8): VLA 조작 중 냉장고 문 · 팔이 라이다 시야를 가리면
odom 이 발산하는 문제가 있다. 스캔 단위 거부(rollback) 패치는 오히려 발산을 일으켜 **폐기**\ 했고, 지금은
FAST-LIO 원본에 스캔별 지표를 로그로만 남긴다 (``[lio_metrics]``). 감지만, 발효 없음.
<<<
RELATIONS:
- TYPE: Parent
  VALUE: SYS-REQ-45
  ROLE: Implements
- TYPE: File
  VALUE: _src/navigation-planner/src/lio/lio_receiver.cpp
- TYPE: File
  VALUE: _src/navigation-planner/src/lio/lio_transform_producer.cpp
- TYPE: File
  VALUE: _src/navigation-planner/src/route_planner/perception/obstacle_mapper.cpp
- TYPE: File
  VALUE: _src/navigation-planner/src/route_planner/perception/obstacle_grid_builder/obstacle_voxel_grid.cpp
- TYPE: File
  VALUE: _src/navigation-planner/lio_engine/lio_bringup.launch.py

[ICD]
UID: ICD-63
TITLE: Camera Depth (ext-sensor → nav-planner)
COMM_TYPE: DDS Topic
SOURCE: ext-sensor-io
TARGET: nav-planner
TOPIC: rt/kist/camera/<name>/depth/rvl
MSG_TYPE: kist_msgs::msg::dds_::CompressedDepthFrame_
QOS: BestEffort
FREQUENCY: 30 Hz
STATEMENT: >>>
RVL 무손실 Z16 + ``depth_scale`` + 카메라 intrinsics(``fx`` / ``fy`` / ``cx`` / ``cy``).
세그멘테이션 결과와 결합해 로봇 좌표계의 labeled cloud 를 만드는 용도였다.
<<<
PRECONDITION: ext-sensor tx 활성
COMMENT: >>>
⚠ **수신측 없음.** navigation-planner 의 ``labeled_cloud`` 소비부가 LIO 재구성 때
``_parked/labeled_cloud/`` 로 옮겨졌다가 레포에서 삭제되었다 (navigation-planner ``b44f6d7``).
지금 이 depth 프레임을 읽는 곳이 시스템에 없다. ext-sensor-io 는 계속 발행한다.

발행측이 살아 있어 노드는 남겨 두었다. navigation-planner 가 세그멘테이션을 되살릴 계획이
없다면 발행 자체를 끄는 것이 대역폭에 낫다 — nav 담당자 확인이 필요하다.

2026-09-28: color · audio 와 함께 타입 이름을 ROS 2 형식으로 바꿨다 (ext-sensor-io ``48c6ca9``).
<<<
RELATIONS:
- TYPE: Parent
  VALUE: SYS-REQ-42
  ROLE: Implements
- TYPE: Parent
  VALUE: SYS-REQ-45
  ROLE: Implements
- TYPE: File
  VALUE: _src/ext-sensor-io/src/realsense/transmitter/depth_publisher.cpp
- TYPE: File
  VALUE: _src/ext-sensor-io/src/realsense/transmitter/rvl_encoder.cpp

[[/SECTION]]

[[SECTION]]
TITLE: 저수준 제어 및 안전

[TEXT]
STATEMENT: >>>
로봇 상태 수신과 관절 명령 발행의 실시간 경로이다.
``SYS-REQ-32`` (양방향 통신) · ``SYS-REQ-34`` (연속 모터 제어) · ``SYS-REQ-35`` (E-STOP) 를 구현한다.
<<<

[TEXT]
STATEMENT: >>>
.. gen_arch: 아래 흐름도는 tools/gen_arch.py 가 이 섹션의 ICD 노드에서 생성한다. 직접 편집하지 말 것.

.. raw:: html

   <div style="overflow-x:auto; max-width:100%;">
   <pre class="mermaid">
      flowchart TB
        subgraph onboard["Unitree G1 (NX) — Onboard"]
          n_G1["G1"]
        end
        subgraph workstation["PC (RTX 4090) — Workstation"]
          n_gearsonic["gearsonic"]
        end

        n_G1 -->|"ICD-4"| n_gearsonic
        n_G1 -->|"ICD-41"| n_gearsonic
        n_gearsonic -->|"ICD-50"| n_G1
        n_gearsonic -->|"ICD-6"| n_G1
        n_G1 -->|"ICD-73"| n_gearsonic
   </pre>
   </div>
<<<

[ICD]
UID: ICD-4
TITLE: LowState (G1 → gearsonic)
COMM_TYPE: DDS Topic
SOURCE: G1
TARGET: gearsonic
TOPIC: rt/lowstate
MSG_TYPE: unitree_hg/LowState (raw DDS)
QOS: BestEffort
FREQUENCY: source-rate (~500 Hz)
STATEMENT: >>>
``motors[29]`` {``q``, ``dq``, ``tau_est``} + pelvis IMU(quat / gyro / accel) + ``tick`` + ``mode_machine``.
CRC32 검증.
<<<
PRECONDITION: G1 전원 · DDS 활성
COMMENT: >>>
소비처 5곳 — gearsonic(제어) · gearsonic ``MotorHealthMonitor`` (fault word · 케이싱/권선 온도 · 토크 정합 감시,
**로그 전용, E-STOP 발효 없음**; gearsonic ``b899bb7`` ``975c3d5``) · vla-inference(정책 관측, 직접 구독) ·
safety-controller(로봇 생존 감시) · navigation-planner(LIO 자세에 허리 관절을 합성해 ``T_odom_pelvis`` 계산).

navigation-planner 는 PC 에서 돌므로 DDS 인터페이스가 로봇 LAN NIC 여야 이 토픽을 받는다.
레포 기본값이 ``lo`` 로 바뀌었다 (navigation-planner ``6299e60``, 같은 PC 시험용) — 실기 배포 때 바꿔야 한다.
<<<
RELATIONS:
- TYPE: Parent
  VALUE: SYS-REQ-32
  ROLE: Implements
- TYPE: Parent
  VALUE: SYS-REQ-31
  ROLE: Implements
- TYPE: Parent
  VALUE: SYS-REQ-35
  ROLE: Implements
- TYPE: File
  VALUE: _src/gearsonic-inference/src/unitree/unitree_state_reader.cpp
- TYPE: File
  VALUE: _src/gearsonic-inference/src/unitree/motor_health_monitor.cpp
- TYPE: File
  VALUE: _src/vla-inference/src/vla/io/unitree/unitree_state_reader.py
- TYPE: File
  VALUE: _src/safety-controller/src/safety/robot_state_monitor.cpp
- TYPE: File
  VALUE: _src/navigation-planner/src/unitree/unitree_state_reader.cpp

[ICD]
UID: ICD-41
TITLE: Secondary IMU (G1 → gearsonic)
COMM_TYPE: DDS Topic
SOURCE: G1
TARGET: gearsonic
TOPIC: rt/secondary_imu
MSG_TYPE: unitree IMU (raw DDS)
QOS: BestEffort
FREQUENCY: source-rate
STATEMENT: >>>
torso IMU: ``quat`` + ``gyro`` (rad/s) + ``accel`` (m/s²) → ImuTorso.
(pelvis IMU는 ``rt/lowstate`` 에 포함.)
<<<
PRECONDITION: G1 DDS 활성
RELATIONS:
- TYPE: Parent
  VALUE: SYS-REQ-32
  ROLE: Implements
- TYPE: File
  VALUE: _src/gearsonic-inference/src/unitree/unitree_state_reader.cpp
- TYPE: File
  VALUE: _src/gearsonic-inference/include/unitree/imu.hpp

[ICD]
UID: ICD-50
TITLE: LowCmd (gearsonic → G1)
COMM_TYPE: DDS Topic
SOURCE: gearsonic
TARGET: G1
TOPIC: rt/lowcmd
MSG_TYPE: unitree_hg/LowCmd (raw DDS)
QOS: Reliable
FREQUENCY: 500 Hz
STATEMENT: >>>
``MotorCommand × 29``: ``q_target``, ``dq_target``, ``kp``, ``kd``, ``tau_ff``. CRC32 검증.
상위가 늦어도 마지막 명령을 반복 발행한다.
<<<
PRECONDITION: gearsonic WBC 활성 + E-STOP 미발효
COMMENT: >>>
E-STOP 발효 시 본 인터페이스의 발행이 차단되어야 하므로 ``SYS-REQ-35`` 를 함께 구현한다.
이 500 Hz 스트림이 그대로 온보드 safety-controller의 데드맨 심박이다 (1 s 침묵 시 내장 제어기 인수).
<<<
RELATIONS:
- TYPE: Parent
  VALUE: SYS-REQ-34
  ROLE: Implements
- TYPE: Parent
  VALUE: SYS-REQ-35
  ROLE: Implements
- TYPE: Parent
  VALUE: SYS-REQ-32
  ROLE: Implements
- TYPE: File
  VALUE: _src/gearsonic-inference/src/unitree/unitree_command_writer.cpp
- TYPE: File
  VALUE: _src/gearsonic-inference/include/control/motor_command.hpp
- TYPE: File
  VALUE: _src/safety-controller/src/safety/pc_link_monitor.cpp

[ICD]
UID: ICD-6
TITLE: Dex3 Hand Cmd (gearsonic → G1)
COMM_TYPE: DDS Topic
SOURCE: gearsonic
TARGET: G1
TOPIC: rt/dex3/{left,right}/cmd
MSG_TYPE: unitree dex3 hand cmd (raw DDS)
QOS: Reliable
FREQUENCY: 100 Hz
STATEMENT: >>>
양손 손가락 7모터 명령 (좌/우 개별 토픽). 상태 피드백(ICD-73)이 있으면 ``HandGuard`` 를 거쳐
정지 토크가 제한된 명령이 나간다.
<<<
PRECONDITION: gearsonic Hand Cmd Writer 활성
RELATIONS:
- TYPE: Parent
  VALUE: SYS-REQ-34
  ROLE: Implements
- TYPE: Parent
  VALUE: SYS-REQ-32
  ROLE: Implements
- TYPE: File
  VALUE: _src/gearsonic-inference/src/unitree/hand_command_writer.cpp
- TYPE: File
  VALUE: _src/gearsonic-inference/include/unitree/hand_command.hpp
- TYPE: File
  VALUE: _src/gearsonic-inference/include/unitree/hand_guard.hpp

[ICD]
UID: ICD-73
TITLE: Dex3 Hand State (G1 → gearsonic)
COMM_TYPE: DDS Topic
SOURCE: G1
TARGET: gearsonic
TOPIC: rt/dex3/{left,right}/state
MSG_TYPE: unitree_hg/HandState (raw DDS)
QOS: BestEffort
FREQUENCY: source-rate
STATEMENT: >>>
양손 7모터의 ``q`` / ``dq`` / ``tau_est`` + 케이싱·권선 온도. ``HandStateReader`` 가 좌/우 토픽을 구독해
``HandState`` 버퍼에 latch 한다(별도 스레드 없음).

소비처: ``HandGuard`` (막힘 시 ``q_cmd = q_meas + clamp(q_des − q_meas, ±tau_max/kp)`` 로 정지 토크 상한,
오차·정지 시간 기반 stall 래치, 온도 즉시 래치) · ``MotorHealthMonitor`` (온도·fault 감시).
<<<
PRECONDITION: Dex3 핸드 전원 · DDS 활성
COMMENT: 상태가 없거나 stale 이면 HandCommandWriter 는 기존 open-loop 로 통과한다 (gearsonic ``fdc9480``).
RELATIONS:
- TYPE: Parent
  VALUE: SYS-REQ-32
  ROLE: Implements
- TYPE: Parent
  VALUE: SYS-REQ-35
  ROLE: Implements
- TYPE: File
  VALUE: _src/gearsonic-inference/src/unitree/hand_state_reader.cpp
- TYPE: File
  VALUE: _src/gearsonic-inference/include/unitree/hand_guard.hpp
- TYPE: File
  VALUE: _src/gearsonic-inference/src/unitree/hand_command_writer.cpp

[[/SECTION]]
